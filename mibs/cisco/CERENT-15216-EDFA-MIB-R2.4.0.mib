-- **************************************************************
--
-- CERENT-15216-EDFA-MIB module
--
-- This module contains the objects and events for the
-- Cisco ONS 15216 EDFA.

-- Copyright (c) 2000-2004 Cisco Systems, Inc.
-- All rights reserved.
--
-- **************************************************************
--
--
CERENT-15216-EDFA-MIB DEFINITIONS ::= BEGIN
    IMPORTS
          TEXTUAL-CONVENTION,
          RowStatus,
	  DisplayString,
	  TimeStamp,
	  AutonomousType,
	  TruthValue,
	  DateAndTime,
          MacAddress
	               FROM SNMPv2-TC
          MODULE-IDENTITY,
          OBJECT-IDENTITY,
          OBJECT-TYPE,
          NOTIFICATION-TYPE,
          Integer32,
          Unsigned32,
          IpAddress
		       FROM SNMPv2-SMI
          cerentModules,
          cerentProducts
		       FROM CERENT-GLOBAL-REGISTRY;

cerent15216EdfaMibModule MODULE-IDENTITY
    LAST-UPDATED
        "0406100000Z" -- (2004/June/10)
    ORGANIZATION
        "Cisco Systems, Inc."
    CONTACT-INFO
        "
                support@cisco.com

        Postal: Cisco Systems, Inc.
                1435, North McDowell Blvd.
                Petaluma CA 94954 USA

           Tel: +1-877-323-7368
        "
    DESCRIPTION
        "
        This module provide the definitions for objects for
        managing ONS 15216 Erbium Doped Fiber Amplifier (EDFA).

	"

    ::= { cerentModules 60 }

-- TEXTUAL-CONVENTIONS --

Cerent15216EdfaBootFileName ::= TEXTUAL-CONVENTION
     STATUS	        current
     DESCRIPTION
			"The name of the file which may include a path
	                 component, e.g. dir1/dir2/name." 
    SYNTAX 	        OCTET STRING ( SIZE ( 0 .. 33  ) )

Cerent15216EdfaModuleIndex ::= TEXTUAL-CONVENTION
    STATUS	        current
    DESCRIPTION
		      	"Index of this module within the chassis."
    SYNTAX 	      	Integer32  ( 1 .. 63  )

Cerent15216EdfaHostName ::= TEXTUAL-CONVENTION
    STATUS	        current
    DESCRIPTION
		       	"A host name."
    SYNTAX 	       	OCTET STRING ( SIZE ( 0 .. 15  ) )

Cerent15216EdfaAlarmID ::= TEXTUAL-CONVENTION
	  STATUS	current
	  DESCRIPTION
			"Alarms defined for this product."
	  SYNTAX 	INTEGER  { unknownAlarm ( 1 ),
	                           lcrnt1 ( 2 ) ,
				   lcrnt2 ( 3 ) ,
				   ltmp1 ( 4 ) ,
				   ltmp2 ( 5 ) ,
				   lpout ( 6 ) ,
				   lpin ( 7 ) ,
				   gain ( 8 ) ,
				   ctmp ( 9 ) ,
				   powerBusA ( 10 ) ,
				   powerBusB ( 11 ) ,
				   dbBackup ( 12 ) ,
				   dbRestore ( 13 ) ,
				   swDownload (14 ) }

Cerent15216EdfaAlarmPriority ::= TEXTUAL-CONVENTION
    STATUS	        current
    DESCRIPTION
			"Priority of this alarm."
    SYNTAX 	        INTEGER  { noAlarm ( 1 ) ,
				   info ( 2 ) ,
				   minor ( 3 ) ,
				   major ( 4 ) ,
				   critical ( 5 ) }

Cerent15216EdfaBootImageName ::= TEXTUAL-CONVENTION
    STATUS	        current
    DESCRIPTION
			"The name of the loaded image."
    SYNTAX 	        OCTET STRING ( SIZE ( 0 .. 10  ) )

Cerent15216EdfaUnsigned8 ::= TEXTUAL-CONVENTION
	STATUS		current
	DESCRIPTION
			"8 bit unsiged integer."
	SYNTAX 		Integer32  ( 0 .. 255  )

Cerent15216EdfaAlarmEventType ::= TEXTUAL-CONVENTION
   STATUS		current
   DESCRIPTION
	"The type of event.
	active(1)	active alarm
	cleared(2)	cleared alarm
	trap(3)		trap sent."
   SYNTAX 	INTEGER  { active  ( 1 ),
		           cleared ( 2 ),
			   trap    ( 3 ) }

Cerent15216EdfaIndex ::= TEXTUAL-CONVENTION
	STATUS		current
	DESCRIPTION
			"Simple Index variable for table."
	SYNTAX 		Integer32  ( 1 .. 2048  )

Cerent15216EdfaDateAndTimeString ::= TEXTUAL-CONVENTION
	STATUS		current
	DESCRIPTION
	    "A date and time.
	    The format is YYYY-MM-DD,hh:mm:ss:dd sTT:SS
            where
                  YYYY = year        (1996..)
                  MM   = month       (1..12)
                  DD   = day         (1..31)
                  hh   = hour        (0..23)
                  mm   = minute      (0..59)
                  ss   = second      (0..59)
                  dd   = deci-second (0..9)
              optionally followed by
                  s    = sign	     ('+' or '-')
                  TT   = timezone    (-23..23)
                  SS   = saving      (-59..59)"
	SYNTAX 	  OCTET STRING ( SIZE ( 0 .. 32  ) )

Cerent15216EdfaDescr32 ::= TEXTUAL-CONVENTION
	STATUS	        current
	DESCRIPTION
			"A short description of an entity."
	SYNTAX 		OCTET STRING ( SIZE ( 0 .. 32  ) )

Cerent15216EdfaDescr ::= TEXTUAL-CONVENTION
	STATUS	        current
	DESCRIPTION
			"A short description of an entity."
	SYNTAX 		OCTET STRING ( SIZE ( 0 .. 64  ) )

Cerent15216EdfaDescr10 ::= TEXTUAL-CONVENTION
	STATUS	        current
	DESCRIPTION
			"A short description of an entity."
	SYNTAX 		OCTET STRING ( SIZE ( 0 .. 10  ) )

Cerent15216EdfaUInteger8 ::= TEXTUAL-CONVENTION
	STATUS	        current
	DESCRIPTION
			"8 bit unsiged integer."
	SYNTAX 		Integer32 ( 0 .. 255  )

Cerent15216EdfaAlarmState ::= TEXTUAL-CONVENTION
	STATUS		current
	DESCRIPTION
	               "State of this alarm."
	SYNTAX 	       INTEGER  { active   ( 1 ) ,
			          disabled ( 2 ) ,
				  cleared  ( 3 ) }

Cerent15216EdfaDCVoltage ::= TEXTUAL-CONVENTION
	STATUS		current
	DESCRIPTION
	                "DC Voltage measurement is given in units of 0.1V.
                         For example if an object defined as this type has a
                         value of 52 then the value is actually 5.2V"
	SYNTAX INTEGER (0..9999)

Cerent15216EdfaPowerBusDCVoltage ::= TEXTUAL-CONVENTION
	STATUS		current
	DESCRIPTION
	                "DC Voltage measurement is given in units of -0.1V.
                         For example if an object defined as this type 
                         has a value of 52 then the value is actually 5.2V."
	SYNTAX INTEGER (350..700)

Cerent15216EdfaPowerBusMode ::= TEXTUAL-CONVENTION
	STATUS 	       current
	DESCRIPTION
	              "Power BUS mode. Simplex mode requires only power to 
		      BUS A. Duplex Mode requires power to both BUS A & BUS B."
	SYNTAX 	      INTEGER { simplex( 1 ), 
	                        duplex( 2 ) }

Cerent15216EdfaPumpControlValue ::= TEXTUAL-CONVENTION
        STATUS        current
        DESCRIPTION
                "Laser pump value. In Units of 0.1mW, 0.1mA or 0.1dB depending 
                on pump control mode."
        SYNTAX INTEGER (0..3000)

Cerent15216EdfaImageType ::= TEXTUAL-CONVENTION
	STATUS		current
	DESCRIPTION
		       "What type of image is this."
	SYNTAX 		INTEGER  { bootLoader ( 1 ) ,
				   runTime ( 2 ) }

Cerent15216EdfaBootEntryIndex ::= TEXTUAL-CONVENTION
	STATUS		current
	DESCRIPTION
			"The index of this boot entry for this
			module."
	SYNTAX 		Integer32  ( 1 .. 4  )

Cerent15216EdfaDateAndTimeFormsString ::= TEXTUAL-CONVENTION
	STATUS		current
	DESCRIPTION
		"A date and time, in the forms format.
	        The format is MM/DD/YYYY hh:mm:ss
                where
                  MM   = month       (01..12)
                  DD   = day         (01..31)
                  YYYY = year        (1996..)
                  hh   = hour        (00..23)
                  mm   = minute      (00..59)
                  ss   = second      (00..59)"
	SYNTAX 		OCTET STRING ( SIZE ( 14 .. 19  ) )

Cerent15216EdfaSlot ::= TEXTUAL-CONVENTION
	STATUS		current
	DESCRIPTION
		      "The number of this slot within the
		      chassis.
	              -1 implies no slot."
	SYNTAX 		Integer32  ( -1 .. 15  )

Cerent15216EdfaActionStatus ::= TEXTUAL-CONVENTION
	STATUS		current
	DESCRIPTION
			"The status of the action."
	SYNTAX 		INTEGER  { idle ( 1 ) ,
			           pending ( 2 ) ,
				   inProgress ( 3 ) ,
				   aborted ( 4 ) }

Cerent15216EdfaControl ::= TEXTUAL-CONVENTION
	STATUS		current
	DESCRIPTION
		"To control a process or device."
	SYNTAX 		INTEGER  { enabled ( 1 ) ,
	                           disabled ( 2 ) }

Cerent15216EdfaPumpNumber ::= TEXTUAL-CONVENTION
	STATUS		current
	DESCRIPTION
		"Laser pump number."
	SYNTAX 		Integer32  ( 1 .. 2  )

Cerent15216EdfaRevision ::= TEXTUAL-CONVENTION
	STATUS		current
	DESCRIPTION
		"Revision Number Component."
	SYNTAX 		Integer32 ( 0 .. 255  )

Cerent15216EdfaAction ::= TEXTUAL-CONVENTION
	STATUS		current
	DESCRIPTION
		"Perform this action by setting the value
		'perform'."
	SYNTAX 		INTEGER  { idle ( 1 ) ,
			           perform ( 2 ) ,
				   abort ( 3 ) }

Cerent15216EdfaControlMode ::= TEXTUAL-CONVENTION
	STATUS		current
	DESCRIPTION
		"Edfa control mode."
	SYNTAX 		INTEGER  { constGainTempComp ( 2 ) ,
				   constOutputPower ( 3 ) ,
				   constCurrent ( 4 ) ,
				   constPower ( 5 ) ,
				   idle ( 6 ) }

Cerent15216EdfaBootSource ::= TEXTUAL-CONVENTION
	STATUS		current
	DESCRIPTION
		"The list of boot source types."
	SYNTAX 		INTEGER  { tftp ( 1 ) ,
				   flash ( 2 ) ,
				   bootp ( 3 ) ,
				   shell ( 4 ) ,
				   noLoad ( 5 ) }

Cerent15216EdfaPort ::= TEXTUAL-CONVENTION
	STATUS		current
	DESCRIPTION
		"The port number within the card.
		0 implies no port."
	SYNTAX 		Integer32  ( 0 .. 15  )

--
-- Objects
--

cerent15216EdfaMib	OBJECT-IDENTITY
	STATUS		current
	DESCRIPTION
		        "The is the node under which all Cisco
			ONS 15216 EDFA specific mib objects are
			located."
	::=  {  cerentProducts  30 }

cerent15216EdfaReg	OBJECT-IDENTITY
	STATUS		current
	DESCRIPTION	"Sub-tree for registrations."
	::=  {  cerent15216EdfaMib  1  }

cerent15216EdfaGeneric	OBJECT-IDENTITY
	STATUS		current
	DESCRIPTION	"Sub-tree for common objects and event
	                definitions."
	::=  {  cerent15216EdfaMib  2  }

cerent15216EdfaSpecific	OBJECT-IDENTITY
	STATUS		current
	DESCRIPTION	"Sub-tree for specific objects and event
	                definitions."
	::=  {  cerent15216EdfaMib  3  }

cerent15216EdfaProduct	OBJECT-IDENTITY
	STATUS		current
	DESCRIPTION	"Sub-tree for all products
	                registrations."
	::=  {  cerent15216EdfaReg  1  }

cerent15216EdfaAlarms	OBJECT-IDENTITY
	STATUS		current
	DESCRIPTION	"Sub-tree to register the Object
	                Identifiers for Alarms."
	::=  {  cerent15216EdfaReg  4  }

cerent15216EdfaGenericCommon	OBJECT-IDENTITY
	STATUS		current
	DESCRIPTION	"Sub-tree for all common objects and
	                event definitions."
	::=  {  cerent15216EdfaGeneric  1  }

cerent15216EdfaGenericEmbedded	OBJECT-IDENTITY
	STATUS		current
	DESCRIPTION	"Sub-tree for all common embedded system
	                objects	and event definitions."
	::=  {  cerent15216EdfaGeneric  2  }

cerent15216EdfaGenericSrom	OBJECT-IDENTITY
	STATUS		current
	DESCRIPTION	"Sub-tree for all common embedded system
	                SROM object and event definitions."
	::=  {  cerent15216EdfaGeneric  4  }

cerent15216EdfaSpecificEmbedded	OBJECT-IDENTITY
	STATUS		current
	DESCRIPTION	"Sub-tree for specific embedded system
	                objects	and event definitions."
	::=  {  cerent15216EdfaSpecific  2  }

cerent15216EdfaSpecificEmbMisc	OBJECT-IDENTITY
	STATUS		current
	DESCRIPTION	"Sub-tree for miscelaneous specific
	                objects and event definitions."
	::=  {  cerent15216EdfaSpecificEmbedded  2  }

-- boot

cerent15216EdfaBootMib	OBJECT-IDENTITY
	STATUS		current
	DESCRIPTION	"Attachment point for the Module Boot
	                MIB."
	::=  {  cerent15216EdfaGenericEmbedded  8  }

cerent15216EdfaBootConf	OBJECT-IDENTITY
	STATUS		current
	DESCRIPTION	"Conformance definitions."
	::=  {  cerent15216EdfaBootMib  1  }

cerent15216EdfaBootObjects	OBJECT-IDENTITY
	STATUS		current
	DESCRIPTION	"Object Definitions."
	::=  {  cerent15216EdfaBootMib  2  }

cerent15216EdfaBootActions	OBJECT-IDENTITY
	STATUS		current
	DESCRIPTION	"Action Definitions."
	::=  {  cerent15216EdfaBootMib  3  }

cerent15216EdfaBootEvents	OBJECT-IDENTITY
	STATUS		current
	DESCRIPTION	"Event Definitions."
	::=  {  cerent15216EdfaBootMib  4  }

cerent15216EdfaBootGroups	OBJECT-IDENTITY
	STATUS		current
	DESCRIPTION	"Object/Notification Group definitions."
	::=  {  cerent15216EdfaBootConf  1  }

cerent15216EdfaBootCompls	OBJECT-IDENTITY
	STATUS		current
	DESCRIPTION	"Module Compliance definitions."
	::=  {  cerent15216EdfaBootConf  2  }

cerent15216EdfaBootEventsV2	OBJECT-IDENTITY
	STATUS		current
	DESCRIPTION	"V2SMI Event Definitions."
	::=  {  cerent15216EdfaBootEvents  0  }

-- boot table

cerent15216EdfaBootTable	OBJECT-TYPE
	SYNTAX		SEQUENCE  OF  Cerent15216EdfaBootEntry
	MAX-ACCESS	not-accessible
	STATUS	current
	DESCRIPTION	"The boot source table.
			This table contains the boot sources used
	                to load the modules.  Each module tries
			it's sources in turn until an image is
			successfully loaded.
	                This table contains up to 4 entries per
			bootable module."
	::=  { cerent15216EdfaBootObjects  1 }

cerent15216EdfaBootEntry	OBJECT-TYPE
	SYNTAX		Cerent15216EdfaBootEntry
	MAX-ACCESS	not-accessible
	STATUS	current
	DESCRIPTION	"The boot entry."
	INDEX		{  cerent15216EdfaBootModuleIndex,
			   cerent15216EdfaBootEntryIndex  }
	::=  { cerent15216EdfaBootTable 1 }

Cerent15216EdfaBootEntry  ::=  SEQUENCE {
	cerent15216EdfaBootModuleIndex
			        Cerent15216EdfaModuleIndex,
	cerent15216EdfaBootEntryIndex
  			        Cerent15216EdfaBootEntryIndex,
	cerent15216EdfaBootType  
	                        Cerent15216EdfaBootSource,
	cerent15216EdfaBootIpAddress  
                                IpAddress,
	cerent15216EdfaBootFileName  
                                Cerent15216EdfaBootFileName
	}


cerent15216EdfaBootModuleIndex	OBJECT-TYPE
	SYNTAX		Cerent15216EdfaModuleIndex
	MAX-ACCESS	not-accessible
	STATUS		current
	DESCRIPTION	"The index of this module."
	::=  {  cerent15216EdfaBootEntry  1  }


cerent15216EdfaBootEntryIndex	OBJECT-TYPE
	SYNTAX		Cerent15216EdfaBootEntryIndex
	MAX-ACCESS	not-accessible
	STATUS		current
	DESCRIPTION	"The index of this boot entry for this
	                module."
	::=  {  cerent15216EdfaBootEntry  2  }


cerent15216EdfaBootType	OBJECT-TYPE
	SYNTAX		Cerent15216EdfaBootSource
	MAX-ACCESS	read-write
	STATUS		current
	DESCRIPTION	"The boot record type"
	DEFVAL			{ flash }
	::=  {  cerent15216EdfaBootEntry  3  }


cerent15216EdfaBootIpAddress	OBJECT-TYPE
	SYNTAX		IpAddress
	MAX-ACCESS	read-write
	STATUS		current
	DESCRIPTION	"IP address for boot server when using
	                TFTP or bootp, 0.0.0.0 otherwise."
	DEFVAL			{ '00000000'H }
	::=  {  cerent15216EdfaBootEntry  4  }


cerent15216EdfaBootFileName	OBJECT-TYPE
	SYNTAX		Cerent15216EdfaBootFileName
	MAX-ACCESS	read-write
	STATUS		current
	DESCRIPTION	"The file to be loaded.
	                 This may include a path component.  For
	                 example if BootType is TFTP, this object
	                 represents the location of the file relative
	                 to the TFTP server's root directory and may
	                 have a form like images/image1."
	::=  {  cerent15216EdfaBootEntry  5  }

-- boot image table

cerent15216EdfaBootImageTable	OBJECT-TYPE
	SYNTAX		SEQUENCE  OF
	                    Cerent15216EdfaBootImageEntry
	MAX-ACCESS	not-accessible
	STATUS	current
	DESCRIPTION	"The Image software table.
	                This table contains the boot and running
	                software image name and revision
			information for each bootable module."
	::=  { cerent15216EdfaBootObjects  3 }

cerent15216EdfaBootImageEntry	OBJECT-TYPE
	SYNTAX		Cerent15216EdfaBootImageEntry
	MAX-ACCESS	not-accessible
	STATUS	current
	DESCRIPTION	"The image entry."
	INDEX		{  cerent15216EdfaBootImageModuleIndex,
			   cerent15216EdfaBootImageType  }
	::=  { cerent15216EdfaBootImageTable 1 }

Cerent15216EdfaBootImageEntry  ::=  SEQUENCE {
	cerent15216EdfaBootImageModuleIndex
			Cerent15216EdfaModuleIndex,
	cerent15216EdfaBootImageType
			Cerent15216EdfaImageType,
	cerent15216EdfaBootImageName
			Cerent15216EdfaBootImageName,
	cerent15216EdfaBootImageFileName
			Cerent15216EdfaBootFileName,
	cerent15216EdfaBootImageRevMajor
			Cerent15216EdfaRevision,
	cerent15216EdfaBootImageRevMinor
			Cerent15216EdfaRevision,
	cerent15216EdfaBootImageRevInterim
			Cerent15216EdfaRevision
	}


cerent15216EdfaBootImageModuleIndex	OBJECT-TYPE
	SYNTAX		Cerent15216EdfaModuleIndex
	MAX-ACCESS	not-accessible
	STATUS		current
	DESCRIPTION	"The index of this module."
	::=  {  cerent15216EdfaBootImageEntry  1  }


cerent15216EdfaBootImageType	OBJECT-TYPE
	SYNTAX		Cerent15216EdfaImageType
	MAX-ACCESS	not-accessible
	STATUS		current
	DESCRIPTION	"The type of this image."
	::=  {  cerent15216EdfaBootImageEntry  2  }


cerent15216EdfaBootImageName	OBJECT-TYPE
	SYNTAX		Cerent15216EdfaBootImageName
	MAX-ACCESS	read-only
	STATUS		current
	DESCRIPTION	"The name of the image."
	::=  {  cerent15216EdfaBootImageEntry  3  }


cerent15216EdfaBootImageFileName	OBJECT-TYPE
	SYNTAX		Cerent15216EdfaBootFileName
	MAX-ACCESS	read-only
	STATUS		current
	DESCRIPTION	"The file name of the image with no path
	                 component." 
	::=  {  cerent15216EdfaBootImageEntry  4  }


cerent15216EdfaBootImageRevMajor	OBJECT-TYPE
	SYNTAX		Cerent15216EdfaRevision
	MAX-ACCESS	read-only
	STATUS		current
	DESCRIPTION	"The major revision number of the image."
	::=  {  cerent15216EdfaBootImageEntry  5  }


cerent15216EdfaBootImageRevMinor	OBJECT-TYPE
	SYNTAX		Cerent15216EdfaRevision
	MAX-ACCESS	read-only
	STATUS		current
	DESCRIPTION	"The minor revision number of the image."
	::=  {  cerent15216EdfaBootImageEntry  6  }


cerent15216EdfaBootImageRevInterim	OBJECT-TYPE
	SYNTAX		Cerent15216EdfaRevision
	MAX-ACCESS	read-only
	STATUS		current
	DESCRIPTION	"The interim revision number of the
			image."
	::=  {  cerent15216EdfaBootImageEntry  7  }

-- agent

cerent15216EdfaAgentMib	OBJECT-IDENTITY
	STATUS		current
	DESCRIPTION	"Attachment point for the Agent MIB."
	::=  {  cerent15216EdfaGenericCommon  3  }

cerent15216EdfaAgentConf	OBJECT-IDENTITY
	STATUS		current
	DESCRIPTION	"Conformance definitions."
	::=  {  cerent15216EdfaAgentMib  1  }

cerent15216EdfaAgentObjects	OBJECT-IDENTITY
	STATUS		current
	DESCRIPTION	"Object Definitions."
	::=  {  cerent15216EdfaAgentMib  2  }

cerent15216EdfaAgentActions	OBJECT-IDENTITY
	STATUS		current
	DESCRIPTION	"Action Definitions."
	::=  {  cerent15216EdfaAgentMib  3  }

cerent15216EdfaAgentEvents	OBJECT-IDENTITY
	STATUS		current
	DESCRIPTION	"Event Definitions."
	::=  {  cerent15216EdfaAgentMib  4  }

cerent15216EdfaAgentGroups	OBJECT-IDENTITY
	STATUS		current
	DESCRIPTION	"Object/Notification Group definitions."
	::=  {  cerent15216EdfaAgentConf  1  }

cerent15216EdfaAgentCompls	OBJECT-IDENTITY
	STATUS		current
	DESCRIPTION	"Module Compliance definitions."
	::=  {  cerent15216EdfaAgentConf  2  }

cerent15216EdfaAgentCommObjects	OBJECT-IDENTITY
	STATUS		current
	DESCRIPTION	"Community Object Definitions."
	::=  {  cerent15216EdfaAgentObjects  1  }

cerent15216EdfaAgentViewObjects	OBJECT-IDENTITY
	STATUS		current
	DESCRIPTION	"View Object Definitions."
	::=  {  cerent15216EdfaAgentObjects  2  }

cerent15216EdfaAgentConfigurationObjects	OBJECT-IDENTITY
	STATUS		current
	DESCRIPTION	"Configuration Object Definitions."
	::=  {  cerent15216EdfaAgentObjects  3  }

cerent15216EdfaActionOpGroup	OBJECT-IDENTITY
	STATUS		current
	DESCRIPTION	"Operations on the agent."
	::=  {  cerent15216EdfaAgentActions  1  }

cerent15216EdfaAgentEventsV2	OBJECT-IDENTITY
	STATUS		current
	DESCRIPTION	"V2SMI Event Definitions."
	::=  {  cerent15216EdfaAgentEvents  0  }

-- community table

cerent15216EdfaCommunityTable	OBJECT-TYPE
	SYNTAX		SEQUENCE  OF
			    Cerent15216EdfaCommunityEntry
	MAX-ACCESS	not-accessible
	STATUS	current
	DESCRIPTION	"The community database.
	    A multi-step set operation is used for row creation."
	::=  { cerent15216EdfaAgentCommObjects  2 }

cerent15216EdfaCommunityEntry	OBJECT-TYPE
	SYNTAX		Cerent15216EdfaCommunityEntry
	MAX-ACCESS	not-accessible
	STATUS	current
	DESCRIPTION	"The access privileges and MIB view
	for a particular community."
	INDEX		{  cerent15216EdfaCommIndex  }
	::=  { cerent15216EdfaCommunityTable 1 }

Cerent15216EdfaCommunityEntry  ::=  SEQUENCE {
	cerent15216EdfaCommIndex  Cerent15216EdfaIndex,
	cerent15216EdfaCommName  OCTET STRING,
	cerent15216EdfaCommViewIndex  Cerent15216EdfaIndex,
	cerent15216EdfaCommPrivileges  Integer32,
	cerent15216EdfaCommSrcIPAddr  IpAddress,
	cerent15216EdfaCommNetMask  IpAddress,
	cerent15216EdfaCommStatus  RowStatus
	}

cerent15216EdfaCommIndex	OBJECT-TYPE
	SYNTAX		Cerent15216EdfaIndex
	MAX-ACCESS	not-accessible
	STATUS		current
	DESCRIPTION	"A community index uniquely identifying a
	                particular SNMPv1/v2c community."
	::=  {  cerent15216EdfaCommunityEntry  1  }


cerent15216EdfaCommName	OBJECT-TYPE
	SYNTAX		OCTET STRING  ( SIZE ( 0 .. 64  ) )
	MAX-ACCESS	read-create
	STATUS		current
	DESCRIPTION	"The community name, which is used in the
                        SNMP pdu's belonging to this community."
	DEFVAL			{ ''H }
	::=  {  cerent15216EdfaCommunityEntry  2  }


cerent15216EdfaCommViewIndex	OBJECT-TYPE
	SYNTAX		Cerent15216EdfaIndex
	MAX-ACCESS	read-create
	STATUS		current
	DESCRIPTION	"The index value for the view table
			entries used by this community.  0 is a
			special case meaning unset.  An entry
			cannot be set to active until this value
			has been set."
	DEFVAL			{ 1 }
	::=  {  cerent15216EdfaCommunityEntry  3  }


cerent15216EdfaCommPrivileges	OBJECT-TYPE
	SYNTAX		Integer32  ( 0 .. 255  )
	MAX-ACCESS	read-create
	STATUS		current
	DESCRIPTION	"The access privileges which govern what
	                management operations a particular
	                community may perform.  These privileges
	                are specified as a sum of values, where
	                each value specifies a SNMP PDU type by
	                which the subject party may request a
	                permitted operation.  The value for a
	                particular PDU type is computed as 2
	                raised to the value of the ASN.1
	                context-specific tag for the appropriate
	                SNMP PDU type.  The values are:

	                Get         :   1
	                GetNext     :   2
	                Response    :   4
	                Set         :   8
	                SNMPv1-Trap :  16
	                GetBulk     :  32
	                Inform      :  64
	                SNMPv2-Trap : 128

			The null set is represented by the value
	                zero."
	DEFVAL			{ 35 }
	::=  {  cerent15216EdfaCommunityEntry  4  }


cerent15216EdfaCommSrcIPAddr	OBJECT-TYPE
	SYNTAX		IpAddress
	MAX-ACCESS	read-create
	STATUS		current
	DESCRIPTION	"The IP address from which network
	                management traffic for this community is
	                received.  The value 0.0.0.0 is a
	                special case meaning any IP address."
	DEFVAL			{ '00000000'H }
	::=  {  cerent15216EdfaCommunityEntry  5  }


cerent15216EdfaCommNetMask	OBJECT-TYPE
	SYNTAX		IpAddress
	MAX-ACCESS	read-create
	STATUS		current
	DESCRIPTION	"The subnet mask to be logically ANDed
	                with the SrcIPAddr IP address when
	                verifying the community string."
	DEFVAL			{ '00000000'H }
	::=  {  cerent15216EdfaCommunityEntry  6  }


cerent15216EdfaCommStatus	OBJECT-TYPE
	SYNTAX		RowStatus
	MAX-ACCESS	read-create
	STATUS		current
	DESCRIPTION	"The status of this conceptual row in the
			communityTable."
	::=  {  cerent15216EdfaCommunityEntry  7  }

-- comm trap table

cerent15216EdfaCommTrapTable	OBJECT-TYPE
	SYNTAX		SEQUENCE  OF
	                    Cerent15216EdfaCommTrapEntry 
	MAX-ACCESS	not-accessible
	STATUS	current
	DESCRIPTION	"The trap destinations database.
	    A multi-step set operation is used for row creation."
	::=  { cerent15216EdfaAgentCommObjects  4 }

cerent15216EdfaCommTrapEntry	OBJECT-TYPE
	SYNTAX		Cerent15216EdfaCommTrapEntry
	MAX-ACCESS	not-accessible
	STATUS	current
	DESCRIPTION	"The information for a trap destination."
	INDEX		{  cerent15216EdfaCommTrapIndex  }
	::=  { cerent15216EdfaCommTrapTable 1 }

Cerent15216EdfaCommTrapEntry  ::=  SEQUENCE {
	cerent15216EdfaCommTrapIndex  Cerent15216EdfaIndex,
	cerent15216EdfaCommTrapCommunity  OCTET STRING,
	cerent15216EdfaCommTrapDestIPAddress  IpAddress,
	cerent15216EdfaCommTrapDestUDPPort  Integer32,
	cerent15216EdfaCommTrapViewIndex  Cerent15216EdfaIndex,
	cerent15216EdfaCommTrapVersion  INTEGER,
	cerent15216EdfaCommTrapStatus  RowStatus
	}


cerent15216EdfaCommTrapIndex	OBJECT-TYPE
	SYNTAX		Cerent15216EdfaIndex
	MAX-ACCESS	not-accessible
	STATUS		current
	DESCRIPTION	"The index of this trap destination."
	::=  {  cerent15216EdfaCommTrapEntry  1  }


cerent15216EdfaCommTrapCommunity	OBJECT-TYPE
	SYNTAX		OCTET STRING  ( SIZE ( 0 .. 64  ) )
	MAX-ACCESS	read-create
	STATUS		current
	DESCRIPTION	"The trap destination community name."
	DEFVAL			{ ''H }
	::=  {  cerent15216EdfaCommTrapEntry  2  }


cerent15216EdfaCommTrapDestIPAddress	OBJECT-TYPE
	SYNTAX		IpAddress
	MAX-ACCESS	read-create
	STATUS		current
	DESCRIPTION	"The trap destination IP Address."
	DEFVAL			{ '00000000'H }
	::=  {  cerent15216EdfaCommTrapEntry  3  }


cerent15216EdfaCommTrapDestUDPPort	OBJECT-TYPE
	SYNTAX		Integer32  ( 0 .. 65535  )
	MAX-ACCESS	read-create
	STATUS		current
	DESCRIPTION	"The trap destination UDP port."
	DEFVAL			{ 162 }
	::=  {  cerent15216EdfaCommTrapEntry  4  }


cerent15216EdfaCommTrapViewIndex	OBJECT-TYPE
	SYNTAX		Cerent15216EdfaIndex
	MAX-ACCESS	read-create
	STATUS		current
	DESCRIPTION	"The trap destination MIB view index.
			A trap may be sent to this destination
	                if it is contained within this MIB
	                view. 0 implies no MIB view."
	DEFVAL			{ 1 }
	::=  {  cerent15216EdfaCommTrapEntry  5  }


cerent15216EdfaCommTrapVersion	OBJECT-TYPE
	SYNTAX		INTEGER  { v1 ( 1 ) , v2 ( 2 ) }
	MAX-ACCESS	read-create
	STATUS		current
	DESCRIPTION	"The trap version number."
	DEFVAL			{ v1 }
	::=  {  cerent15216EdfaCommTrapEntry  6  }


cerent15216EdfaCommTrapStatus	OBJECT-TYPE
	SYNTAX		RowStatus
	MAX-ACCESS	read-create
	STATUS		current
	DESCRIPTION	"The status of this conceptual row in the
			cerent15216EdfaCommunityTrapTable."
	::=  {  cerent15216EdfaCommTrapEntry  7  }

-- view table 

cerent15216EdfaViewTable	OBJECT-TYPE
	SYNTAX		SEQUENCE  OF  Cerent15216EdfaViewEntry
	MAX-ACCESS	not-accessible
	STATUS	current
	DESCRIPTION	"Locally held information about the MIB
	                views known to this SNMPv2 entity.

			Each SNMP community has a single MIB
	                view which is defined by two collections
	                of view subtrees: the included view
	                subtrees, and the excluded view
	                subtrees.  Every such subtree, both
	                included and excluded, is defined in
	                this table.

			To determine if a particular object
	                instance is in a particular MIB view,
	                compare the object instance's OBJECT
	                IDENTIFIER with each of the MIB view's
	                entries in this table.  If none match,
	                then the object instance is not in the
	                MIB view.  If one or more match, then
	                the object instance is included in, or
	                excluded from, the MIB view according to
	                the value of viewType in the entry whose
	                value of viewSubtree has the most
	                sub-identifiers.  If multiple entries
	                match and have the same number of
	                sub-identifiers, then the
	                lexicographically greatest instance of
	                viewType determines the inclusion or
	                exclusion.

			An object instance's OBJECT IDENTIFIER X
	                matches an entry in this table when the
	                number of sub-identifiers in X is at
	                least as many as in the value of
	                viewSubtree for the entry, and each
	                sub-identifier in the value of
	                viewSubtree matches its corresponding
	                sub-identifier in X.  Two
	                sub-identifiers match either if the
	                corresponding bit of viewMask is zero
	                (the 'wild card'value), or if they are
	                equal.

			Due to this 'wild card' capability, we
	                introduce the term, a 'family' of view
	                subtrees, to refer to the set of
	                subtrees defined by a particular
	                combination of values of viewSubtree and
	                viewMask.  In the case where no 'wild
	                card' is defined in viewMask, the family
	                of view subtrees reduces to a single
	                view subtree.

			A multi-step set operation is used for
	                row creation.
			
			This is almost identival to RFC1447's view
	                table with the difference being that the
	                StorageType object is not defined here."
	::=  { cerent15216EdfaAgentViewObjects  2 }

cerent15216EdfaViewEntry	OBJECT-TYPE
	SYNTAX		Cerent15216EdfaViewEntry
	MAX-ACCESS	not-accessible
	STATUS	current
	DESCRIPTION	"Information on a particular family of
	                view subtrees included in or excluded
	                from a particular SNMP communitiy MIB
	                view." 
	INDEX		{  cerent15216EdfaViewIndex,
			   IMPLIED cerent15216EdfaViewSubtree  }
	::=  { cerent15216EdfaViewTable 1 }

Cerent15216EdfaViewEntry  ::=  SEQUENCE {
	cerent15216EdfaViewIndex  Cerent15216EdfaIndex,
	cerent15216EdfaViewSubtree  OBJECT IDENTIFIER,
	cerent15216EdfaViewMask  OCTET STRING,
	cerent15216EdfaViewType  INTEGER,
	cerent15216EdfaViewStatus  RowStatus
	}


cerent15216EdfaViewIndex	OBJECT-TYPE
	SYNTAX		Cerent15216EdfaIndex
	MAX-ACCESS	not-accessible
	STATUS		current
	DESCRIPTION	"A unique value for each MIB view.  The
	                value for each MIB view must remain
	                constant at least from one
	                re-initialization of the entity's
	                network management system to the next
	                re-initialization." 
	::=  {  cerent15216EdfaViewEntry  1  }


cerent15216EdfaViewSubtree	OBJECT-TYPE
	SYNTAX		OBJECT IDENTIFIER
	MAX-ACCESS	not-accessible
	STATUS		current
	DESCRIPTION	"A MIB subtree."
	::=  {  cerent15216EdfaViewEntry  2  }


cerent15216EdfaViewMask	OBJECT-TYPE
	SYNTAX		OCTET STRING  ( SIZE ( 0 .. 16  ) )
	MAX-ACCESS	read-create
	STATUS		current
	DESCRIPTION	"The bit mask which, in combination with
	the corresponding instance of
	cerent15216EdfaViewSubtree, defines a family of view
	subtrees. 

	Each bit of this bit mask corresponds to a
	sub-identifier of cerent15216EdfaViewSubtree, with the
	most significant bit of the i-th octet of this octet
	string value (extended if necessary, see below)
	corresponding to the (8*i - 7)-th sub-identifier, and
	the least significant bit of the i-th octet of this
	octet string corresponding to the (8*i)-th
	sub-identifier, where i is in the range 1 through 16.

	Each bit of this bit mask specifies whether or not the
	corresponding sub-identifiers must match when
	determining if an OBJECT IDENTIFIER is in this family of
	view subtrees; a '1' indicates that an exact match must
	occur; a '0' indicates 'wild card', i.e., any
	sub-identifier value matches.

	Thus, the OBJECT IDENTIFIER X of an object instance is
	contained in a family of view subtrees if the following
	criteria are met:

	for each sub-identifier of the value of viewSubtree,
	either:

	the i-th bit of cerent15216EdfaViewMask is 0, or
	the i-th sub-identifier of X is equal to
	the i-th sub-identifier of the value of
	cerent15216EdfaViewSubtree. 

	If the value of this bit mask is M bits long and there
	are more than M sub-identifiers in the corresponding
	instance of cerent15216EdfaViewSubtree, then the bit
	mask is extended with 1's to be the required length.

	Note that when the value of this object is the
	zero-length string, this extension rule results in a
	mask of all-1's being used (i.e., no 'wild card'), and
	the family of view subtrees is the one view subtree
	uniquely identified by the corresponding instance of
	cerent15216EdfaViewSubtree."
	DEFVAL			{ ''H }
	::=  {  cerent15216EdfaViewEntry  3  }


cerent15216EdfaViewType	OBJECT-TYPE
	SYNTAX		INTEGER  { included ( 1 ) , excluded ( 2 ) }
	MAX-ACCESS	read-create
	STATUS		current
	DESCRIPTION	"The status of a particular family of
	view subtrees within the particular SNMP community MIB
	view.  The value 'included(1)' indicates that the
	corresponding instances of cerent15216EdfaViewSubtree
	and cerent15216EdfaViewMask define a family of
	viewsubtrees included in the MIB view.  The  value
	'excluded(2)' indicates that the corresponding instances
	of cerent15216EdfaViewSubtree and
	cerent15216EdfaViewMask define a family of view subtrees
	excluded from the MIB view." 
	DEFVAL			{ included }
	::=  {  cerent15216EdfaViewEntry  4  }


cerent15216EdfaViewStatus	OBJECT-TYPE
	SYNTAX		RowStatus
	MAX-ACCESS	read-create
	STATUS		current
	DESCRIPTION	"The status of this conceptual row in the
			cerent15216EdfaViewTable."
	::=  {  cerent15216EdfaViewEntry  5  }

-- agent control

cerent15216EdfaAgentControlGroup	OBJECT-IDENTITY
	STATUS		current
	DESCRIPTION	"Agent Control."
	::=  {  cerent15216EdfaAgentConfigurationObjects  1  }

cerent15216EdfaAgentTrapEnable	OBJECT-TYPE
	SYNTAX		Cerent15216EdfaControl
	MAX-ACCESS	read-write
	STATUS		current
	DESCRIPTION	"Allows the generation of traps from the
			agent."
	DEFVAL			{ enabled }
	::=  {  cerent15216EdfaAgentControlGroup  1  }

cerent15216EdfaAgentNotificationNumber	OBJECT-TYPE
	SYNTAX		Integer32  ( 0 .. 2147483647 )
	MAX-ACCESS	read-only
	STATUS		current
	DESCRIPTION	"The number of traps dispatched since
			reboot."
	::=  {  cerent15216EdfaAgentControlGroup  2  }

cerent15216EdfaActionOpStatus	OBJECT-TYPE
	SYNTAX		Cerent15216EdfaActionStatus
	MAX-ACCESS	read-only
	STATUS		current
	DESCRIPTION	"The status of the current operation."
	::=  {  cerent15216EdfaActionOpGroup  1  }

cerent15216EdfaActionOpResult	OBJECT-TYPE
	SYNTAX		Integer32  ( -2147483647 .. 2147483647 )
	MAX-ACCESS	read-only
	STATUS		current
	DESCRIPTION	"This value is used to save the error
			result (if any) of the last operation. 0
			indicates success."
	DEFVAL			{ 0 }
	::=  {  cerent15216EdfaActionOpGroup  2  }

cerent15216EdfaActionOpReset	OBJECT-TYPE
	SYNTAX		Cerent15216EdfaAction
	MAX-ACCESS	read-write
	STATUS		current
	DESCRIPTION	"This object will reset the Management 
	    Module (not the Optical Module) when the 'perform' 
	    value is written to it. The reset will be delayed a 
	    short period (approximately 2 seconds) to allow SNMP 
	    response to be sent to the manager before the reset 
	    is performed."
	DEFVAL		{ idle }
	::=  {  cerent15216EdfaActionOpGroup  3  }

cerent15216EdfaActionOpSaveConfig	OBJECT-TYPE
	SYNTAX		DisplayString  ( SIZE ( 1 .. 20  ) )
	MAX-ACCESS	read-write
	STATUS		current
	DESCRIPTION	"To save the configuration of the SNMP 
	    agent on the Management Module, write the 
	    destination file name to this object.
	    The most recent vesion of the destination file
	    will be saved as <name>.bak.

	NOTE:	The agent automatically reads the
		configuration from 'snmp.cfg' at startup.
		Saving to other file names will not
	     	change this."
	DEFVAL	  	{ "snmp.cfg" }
	::=  {  cerent15216EdfaActionOpGroup  4  }

--
-- Notifications 
-- 

cerent15216EdfaActionOpFinished	NOTIFICATION-TYPE
	OBJECTS		{ cerent15216EdfaActionOpReset ,
			  cerent15216EdfaActionOpSaveConfig ,
			  cerent15216EdfaActionOpResult  }
	STATUS		current
	DESCRIPTION	"This trap indicates that an operation
			has completed." 
	::=  {  cerent15216EdfaAgentEventsV2  1  }

-- rtc

cerent15216EdfaRtcMib	OBJECT-IDENTITY
	STATUS		current
	DESCRIPTION	"Attachment point for the Real-Time
			Clock MIB." 
	::=  {  cerent15216EdfaGenericEmbedded  13  }

cerent15216EdfaRtcConf	OBJECT-IDENTITY
	STATUS		current
	DESCRIPTION	"Conformance definitions."
	::=  {  cerent15216EdfaRtcMib  1  }

cerent15216EdfaRtcObjects	OBJECT-IDENTITY
	STATUS		current
	DESCRIPTION	"Object Definitions."
	::=  {  cerent15216EdfaRtcMib  2  }

cerent15216EdfaRtcActions	OBJECT-IDENTITY
	STATUS		current
	DESCRIPTION	"Action Definitions."
	::=  {  cerent15216EdfaRtcMib  3  }

cerent15216EdfaRtcEvents	OBJECT-IDENTITY
	STATUS		current
	DESCRIPTION	"Event Definitions."
	::=  {  cerent15216EdfaRtcMib  4  }

cerent15216EdfaRtcGroups	OBJECT-IDENTITY
	STATUS		current
	DESCRIPTION	"Object/Notification Group definitions."
	::=  {  cerent15216EdfaRtcConf  1  }

cerent15216EdfaRtcCompls	OBJECT-IDENTITY
	STATUS		current
	DESCRIPTION	"Module Compliance definitions."
	::=  {  cerent15216EdfaRtcConf  2  }

cerent15216EdfaRtcDateAndTime	OBJECT-IDENTITY
	STATUS		current
	DESCRIPTION	"Current Date and Time Values"
	::=  {  cerent15216EdfaRtcObjects  1  }

cerent15216EdfaRtcEventsV2	OBJECT-IDENTITY
	STATUS		current
	DESCRIPTION	"V2SMI Event Definitions."
	::=  {  cerent15216EdfaRtcEvents  0  }

cerent15216EdfaRtcDateAndTimeLocal	OBJECT-TYPE
	SYNTAX		DateAndTime
	MAX-ACCESS	read-write
	STATUS		current
	DESCRIPTION	"The current local time. Setting this
			value will change the time according to
			the
			cerent15216EdfaRtcDateAndTimeTimezone
			and 
			cerent15216EdfaRtcDateAndTimeSaving
			values. The timezone and saving fields
			of this attribute are thus ignored on
			set." 
	::=  {  cerent15216EdfaRtcDateAndTime  1  }

cerent15216EdfaRtcDateAndTimeGMT	OBJECT-TYPE
	SYNTAX		DateAndTime
	MAX-ACCESS	read-only
	STATUS		current
	DESCRIPTION	"The current GMT time."
	::=  {  cerent15216EdfaRtcDateAndTime  2  }

cerent15216EdfaRtcDateAndTimeLocalString	OBJECT-TYPE
	SYNTAX		Cerent15216EdfaDateAndTimeString
	MAX-ACCESS	read-write
	STATUS		current
	DESCRIPTION	"The current local time."
	::=  {  cerent15216EdfaRtcDateAndTime  3  }

cerent15216EdfaRtcDateAndTimeGMTString	OBJECT-TYPE
	SYNTAX		Cerent15216EdfaDateAndTimeString
	MAX-ACCESS	read-only
	STATUS		current
	DESCRIPTION	"The current GMT time."
	::=  {  cerent15216EdfaRtcDateAndTime  4  }

cerent15216EdfaRtcDateAndTimeTimezone	OBJECT-TYPE
	SYNTAX		Integer32  ( -23 .. 23  )
	MAX-ACCESS	read-write
	STATUS		current
	DESCRIPTION	"The timezone in hours from GMT."
	::=  {  cerent15216EdfaRtcDateAndTime  5  }

cerent15216EdfaRtcDateAndTimeSaving	OBJECT-TYPE
	SYNTAX		Integer32  ( -60 .. 60  )
	MAX-ACCESS	read-write
	STATUS		current
	DESCRIPTION	"The current daylight saving offset in
	in minutes."
	::=  {  cerent15216EdfaRtcDateAndTime  6  }

cerent15216EdfaRtcDateAndTimeFormsString	OBJECT-TYPE
	SYNTAX		Cerent15216EdfaDateAndTimeFormsString
	MAX-ACCESS	read-write
	STATUS		current
	DESCRIPTION	"The current local time."
	::=  {  cerent15216EdfaRtcDateAndTime  7  }

-- srom

cerent15216EdfaSromIpAddrMib	OBJECT-IDENTITY
	STATUS		current
	DESCRIPTION	"Attachment point for the common IP
			address block for the embedded system
			SROMs." 
	::=  {  cerent15216EdfaGenericSrom  2  }

cerent15216EdfaSromIpAddrConf	OBJECT-IDENTITY
	STATUS		current
	DESCRIPTION	"Conformance definitions."
	::=  {  cerent15216EdfaSromIpAddrMib  1  }

cerent15216EdfaSromIpAddrObjects	OBJECT-IDENTITY
	STATUS		current
	DESCRIPTION	"Object Definitions."
	::=  {  cerent15216EdfaSromIpAddrMib  2  }

cerent15216EdfaSromIpAddrActions	OBJECT-IDENTITY
	STATUS		current
	DESCRIPTION	"Action Definitions."
	::=  {  cerent15216EdfaSromIpAddrMib  3  }

cerent15216EdfaSromIpAddrEvents	OBJECT-IDENTITY
	STATUS		current
	DESCRIPTION	"Event Definitions."
	::=  {  cerent15216EdfaSromIpAddrMib  4  }

cerent15216EdfaSromIpAddrGroups	OBJECT-IDENTITY
	STATUS		current
	DESCRIPTION	"Object/Notifcation Group definitions."
	::=  {  cerent15216EdfaSromIpAddrConf  1  }

cerent15216EdfaSromIpAddrCompls	OBJECT-IDENTITY
	STATUS		current
	DESCRIPTION	"Module Compliance definitions."
	::=  {  cerent15216EdfaSromIpAddrConf  2  }

cerent15216EdfaSromIpMgmtGroup	OBJECT-IDENTITY
	STATUS		current
	DESCRIPTION	"Object Definitions for IP addresses for
			device management."
	::=  {  cerent15216EdfaSromIpAddrObjects  1  }

cerent15216EdfaSromIpAddrEventsV2	OBJECT-IDENTITY
	STATUS		current
	DESCRIPTION	"V2SMI Event Definitions."
	::=  {  cerent15216EdfaSromIpAddrEvents  0  }

cerent15216EdfaSromIpMgmtEnetAddress	OBJECT-TYPE
	SYNTAX		IpAddress
	MAX-ACCESS	read-write
	STATUS		current
	DESCRIPTION	"The IP address used by the system's
	Ethernet management port.
	If set to 0.0.0.0 then no IP traffic will be supported
	over the ethernet interface."
	DEFVAL			{ '00000000'H }
	::=  {  cerent15216EdfaSromIpMgmtGroup  1  }

cerent15216EdfaSromIpMgmtEnetSubNetMask	OBJECT-TYPE
	SYNTAX		IpAddress
	MAX-ACCESS	read-write
	STATUS		current
	DESCRIPTION	"The IP Subnetwork mask for the Ethernet
			management port."
	DEFVAL			{ '00000000'H }
	::=  {  cerent15216EdfaSromIpMgmtGroup  2  }

cerent15216EdfaSromIpMgmtDefaultRouterAddress	OBJECT-TYPE
	SYNTAX		IpAddress
	MAX-ACCESS	read-write
	STATUS		current
	DESCRIPTION	"The IP address of the default router
			used by the system. The routers address
			must be on the Ethernet IP subnetwork." 
	DEFVAL			{ '00000000'H }
	::=  {  cerent15216EdfaSromIpMgmtGroup  5  }

cerent15216EdfaSromIpMgmtHostName	OBJECT-TYPE
	SYNTAX		Cerent15216EdfaHostName
	MAX-ACCESS	read-write
	STATUS		current
	DESCRIPTION	"The system's Host Name."
	::=  {  cerent15216EdfaSromIpMgmtGroup  6  }

cerent15216EdfaSromIpMgmtMacAddress	OBJECT-TYPE
	SYNTAX		MacAddress
	MAX-ACCESS	read-only
	STATUS		current
	DESCRIPTION	"The system's MAC address."
	::=  {  cerent15216EdfaSromIpMgmtGroup  7  }

-- event log

cerent15216EdfaLogMib	OBJECT-IDENTITY
	STATUS		current
	DESCRIPTION	"Attachement point for the Log MIB."
	::=  {  cerent15216EdfaGenericEmbedded  1  }

cerent15216EdfaLogConf	OBJECT-IDENTITY
	STATUS		current
	DESCRIPTION	"Conformance definitions."
	::=  {  cerent15216EdfaLogMib  1  }

cerent15216EdfaLogObjects	OBJECT-IDENTITY
	STATUS		current
	DESCRIPTION	"Object Definitions."
	::=  {  cerent15216EdfaLogMib  2  }

cerent15216EdfaLogConfigurationObjects OBJECT-IDENTITY
	STATUS	current
	DESCRIPTION
		"Configuration Object Definitions."
	::= { cerent15216EdfaLogObjects 1 }

cerent15216EdfaLogEventObjects	OBJECT-IDENTITY
	STATUS		current
	DESCRIPTION	"Event Object Definitions."
	::=  {  cerent15216EdfaLogObjects  3  }

cerent15216EdfaLogActions	OBJECT-IDENTITY
	STATUS		current
	DESCRIPTION	"Action Definitions."
	::=  {  cerent15216EdfaLogMib  3  }

cerent15216EdfaLogEvents	OBJECT-IDENTITY
	STATUS		current
	DESCRIPTION	"Event Definitions."
	::=  {  cerent15216EdfaLogMib  4  }

cerent15216EdfaLogEventControl OBJECT-IDENTITY
	STATUS	current
	DESCRIPTION
		"Log event control."
	::= { cerent15216EdfaLogConfigurationObjects 1 }

cerent15216EdfaLogEventClear	OBJECT-TYPE
	SYNTAX		Cerent15216EdfaAction
	MAX-ACCESS	read-write
	STATUS		current
        DESCRIPTION     "Use this attribute to clear all 
	                logged events from the 
			cerent15216EdfaLogEventTable."
	DEFVAL			{ idle }
	::=  {  cerent15216EdfaLogEventControl  5  }

-- the event table

cerent15216EdfaLogEventTable	OBJECT-TYPE
	SYNTAX		SEQUENCE  OF
			    Cerent15216EdfaLogEventEntry
	MAX-ACCESS	not-accessible
	STATUS	current
	DESCRIPTION	"The logged events."
	::=  { cerent15216EdfaLogEventObjects  1 }

cerent15216EdfaLogEventEntry	OBJECT-TYPE
	SYNTAX		Cerent15216EdfaLogEventEntry
	MAX-ACCESS	not-accessible
	STATUS	current
	DESCRIPTION	"A logged event."
	INDEX		{  cerent15216EdfaLogEventIndex  }
	::=  { cerent15216EdfaLogEventTable 1 }

Cerent15216EdfaLogEventEntry  ::=  SEQUENCE {
	cerent15216EdfaLogEventIndex  Cerent15216EdfaIndex,
	cerent15216EdfaLogEventID  AutonomousType,
	cerent15216EdfaLogEventPriority
			Cerent15216EdfaAlarmPriority,
	cerent15216EdfaLogEventType
			Cerent15216EdfaAlarmEventType,
	cerent15216EdfaLogEventSlot  Cerent15216EdfaSlot,
	cerent15216EdfaLogEventPort  Cerent15216EdfaPort,
	cerent15216EdfaLogEventTime  TimeStamp,
	cerent15216EdfaLogEventDateAndTime
			Cerent15216EdfaDateAndTimeString,
	cerent15216EdfaLogEventFormsDateAndTime
			Cerent15216EdfaDateAndTimeFormsString
	}


cerent15216EdfaLogEventIndex	OBJECT-TYPE
	SYNTAX		Cerent15216EdfaIndex
	MAX-ACCESS	not-accessible
	STATUS		current
	DESCRIPTION	"A unique value to identify this logged 
	                event."
	::=  {  cerent15216EdfaLogEventEntry  1  }


cerent15216EdfaLogEventID	OBJECT-TYPE
	SYNTAX		AutonomousType
	MAX-ACCESS	read-only
	STATUS		current
	DESCRIPTION	"The logged event this entry refers to."
	::=  {  cerent15216EdfaLogEventEntry  2  }


cerent15216EdfaLogEventPriority	OBJECT-TYPE
	SYNTAX		Cerent15216EdfaAlarmPriority
	MAX-ACCESS	read-only
	STATUS		current
	DESCRIPTION	"The priority of this logged event."
	::=  {  cerent15216EdfaLogEventEntry  3  }


cerent15216EdfaLogEventType	OBJECT-TYPE
	SYNTAX		Cerent15216EdfaAlarmEventType
	MAX-ACCESS	read-only
	STATUS		current
	DESCRIPTION	"The type of logged event."
	::=  {  cerent15216EdfaLogEventEntry  4  }


cerent15216EdfaLogEventSlot	OBJECT-TYPE
	SYNTAX		Cerent15216EdfaSlot
	MAX-ACCESS	read-only
	STATUS		current
	DESCRIPTION	"Index of the slot reporting the logged 
	                event."
	::=  {  cerent15216EdfaLogEventEntry  6  }

cerent15216EdfaLogEventPort	OBJECT-TYPE
	SYNTAX		Cerent15216EdfaPort
	MAX-ACCESS	read-only
	STATUS		current
	DESCRIPTION	"Index of the port reporting the logged 
	                event."
	::=  {  cerent15216EdfaLogEventEntry  7  }


cerent15216EdfaLogEventTime	OBJECT-TYPE
	SYNTAX		TimeStamp
	MAX-ACCESS	read-only
	STATUS		current
	DESCRIPTION	"The value of sysUpTime when the logged 
	                event happened."
	::=  {  cerent15216EdfaLogEventEntry  8  }


cerent15216EdfaLogEventDateAndTime	OBJECT-TYPE
	SYNTAX		Cerent15216EdfaDateAndTimeString
	MAX-ACCESS	read-only
	STATUS		current
	DESCRIPTION	"The local date and time when the logged 
	                event happened. If the node does not 
			support a run-time clock the string will 
			be blank."
	::=  {  cerent15216EdfaLogEventEntry  9  }


cerent15216EdfaLogEventFormsDateAndTime	OBJECT-TYPE
	SYNTAX		Cerent15216EdfaDateAndTimeFormsString
	MAX-ACCESS	read-only
	STATUS		current
	DESCRIPTION	"The local date and time when the logged 
	                event happened. If the node does not 
			support a run-time clock the string will 
			be blank."
	::=  {  cerent15216EdfaLogEventEntry  10  }

--

cerent15216EdfaAlarmsMisc	OBJECT-IDENTITY
	STATUS		current
	DESCRIPTION	"Miscelaneous sub-system related Alarms."
	::=  {  cerent15216EdfaAlarms  1  }

-- edfa specific

cerent15216EdfaSpecificMib	OBJECT-IDENTITY
	STATUS		current
	DESCRIPTION	"Attachment point for the  MIB."
	::=  {  cerent15216EdfaSpecificEmbMisc  1  }

cerent15216EdfaConf	OBJECT-IDENTITY
	STATUS		current
	DESCRIPTION	"Conformance definitions."
	::=  {  cerent15216EdfaSpecificMib  1  }

cerent15216EdfaGroups	OBJECT-IDENTITY
	STATUS		current
	DESCRIPTION	"Object/Notification Group definitions."
	::=  {  cerent15216EdfaConf  1  }

cerent15216EdfaCompls	OBJECT-IDENTITY
	STATUS		current
	DESCRIPTION	"Module Compliance definitions."
	::=  {  cerent15216EdfaConf  2  }

cerent15216EdfaObjects	OBJECT-IDENTITY
	STATUS		current
	DESCRIPTION	"Object Definitions."
	::=  {  cerent15216EdfaSpecificMib  2  }

cerent15216EdfaCfg	OBJECT-IDENTITY
	STATUS		current
	DESCRIPTION	"Edfa configuration data."
	::=  {  cerent15216EdfaObjects  1  }

cerent15216EdfaStatus	OBJECT-IDENTITY
	STATUS		current
	DESCRIPTION	"Edfa status information."
	::=  {  cerent15216EdfaObjects  2  }

cerent15216EdfaEventObjects	OBJECT-IDENTITY
	STATUS		current
	DESCRIPTION	"Edfa event information."
	::=  {  cerent15216EdfaObjects  3  }

cerent15216EdfaFfsSystem OBJECT-IDENTITY
	STATUS	current
	DESCRIPTION
		"The Flash File System status."
	::= { cerent15216EdfaObjects 4 }

cerent15216EdfaFfsDirectory OBJECT-IDENTITY
	STATUS	current
	DESCRIPTION
		"The Flash File System directory."
	::= { cerent15216EdfaObjects 5 }

cerent15216EdfaFfsActions	OBJECT-IDENTITY
	STATUS		current
	DESCRIPTION	"Action Definitions."
	::=  {  cerent15216EdfaObjects  6  }

cerent15216EdfaActions	OBJECT-IDENTITY
	STATUS		current
	DESCRIPTION	"Action Definitions."
	::=  {  cerent15216EdfaSpecificMib  3  }

cerent15216EdfaEvents	OBJECT-IDENTITY
	STATUS		current
	DESCRIPTION	"Event Definitions."
	::=  {  cerent15216EdfaSpecificMib  4  }

cerent15216EdfaEventsV2	OBJECT-IDENTITY
	STATUS		current
	DESCRIPTION	"V2SMI Event Definitions."
	::=  {  cerent15216EdfaEvents  0  }

-- alarm objects

cerent15216EdfaAlarmLcrnt1	OBJECT-IDENTITY
	STATUS		current
	DESCRIPTION	"Excessive pump current - pump 1.
	    Drive current greater than 95% of end of life value.
	    Current must drop to 90% of end of life value for 
	    alarm to clear."
	::=  {  cerent15216EdfaAlarmsMisc  1  }

cerent15216EdfaAlarmLcrnt2	OBJECT-IDENTITY
	STATUS		current
	DESCRIPTION	"Excessive pump current - pump 2.
	    Drive current greater than 95% of end of life value. 
	    Current must drop to 90% of end of life value for 
	    alarm to clear."
	::=  {  cerent15216EdfaAlarmsMisc  2  }

cerent15216EdfaAlarmLtmp1	OBJECT-IDENTITY
	STATUS		current
	DESCRIPTION	"Pump 1 laser temp. out of range.
	    Chip temperature deviating more than 10 degrees C 
	    from setpoint."
	::=  {  cerent15216EdfaAlarmsMisc  3  }

cerent15216EdfaAlarmLtmp2	OBJECT-IDENTITY
	STATUS		current
	DESCRIPTION	"Pump 2 laser temp. out of range.
	    Chip temperature deviating more than 10 degrees C 
	    from setpoint."
	::=  {  cerent15216EdfaAlarmsMisc  4  }

cerent15216EdfaAlarmLpout	OBJECT-IDENTITY
	STATUS		current
	DESCRIPTION	"Loss of output power.
	    EDFA output power is deviating more than the 
	    prescribed amount from the setpoint." 
	::=  {  cerent15216EdfaAlarmsMisc  5  }

cerent15216EdfaAlarmLpin	OBJECT-IDENTITY
	STATUS		current
	DESCRIPTION	"Loss of input power.
	    EDFA input power is below the loss of signal 
	    threshold."
	::=  {  cerent15216EdfaAlarmsMisc  6  }

cerent15216EdfaAlarmGain	OBJECT-IDENTITY
	STATUS		current
	DESCRIPTION	"Gain out of range.
	    This alarm is only valid when the ONS 15216 EDFA2 is in 
            GAINTEMP mode. It occurs when the value of  OVERALLGAINMEASURED 
            has deviated more than 1.25 dB from the manufacturer-defined set
            point’s allowable range. This condition has a 0.25 dB hysteresis.
            The GAIN alarm is also triggered if the value of INPWRDBM goes 
            outside the manufacturer-defined range by more than 0.7dB. This 
            condition has a 0.2 dB hysteresis.Gain has deviated more than 
            1.25dB from the setpoint, or input power is out of range for 
            setpoint."
	::=  {  cerent15216EdfaAlarmsMisc  7  }

cerent15216EdfaAlarmCtmp	OBJECT-IDENTITY
	STATUS		current
	DESCRIPTION	"Case temperature out of the prescribed
	    range." 
	::=  {  cerent15216EdfaAlarmsMisc  8  }

cerent15216EdfaAlarmPowerBusA OBJECT-IDENTITY
	STATUS	current
	DESCRIPTION
		"The Power BUS A voltage is out of the prescribed range."
	::= { cerent15216EdfaAlarmsMisc 9 }

cerent15216EdfaAlarmPowerBusB OBJECT-IDENTITY
	STATUS	current
	DESCRIPTION
		"The Power BUS B voltage is out of the prescribed range."
	::= { cerent15216EdfaAlarmsMisc 10 }

cerent15216EdfaAlarmDbBackup OBJECT-IDENTITY
        STATUS        current
        DESCRIPTION
                "Database backup in progress."
        ::= { cerent15216EdfaAlarmsMisc 11 }

cerent15216EdfaAlarmDbRestore OBJECT-IDENTITY
        STATUS        current
        DESCRIPTION
                "Database restore in progress."
        ::= { cerent15216EdfaAlarmsMisc 12 }

cerent15216EdfaAlarmSwDownload OBJECT-IDENTITY
        STATUS        current
        DESCRIPTION
                "Software download in progress."
        ::= { cerent15216EdfaAlarmsMisc 13 }

-- edfa cfg

cerent15216EdfaCfgGroup	OBJECT-IDENTITY
	STATUS		current
	DESCRIPTION	"Scalar configuration objects."
	::=  {  cerent15216EdfaCfg  1  }

cerent15216EdfaCfgSaved	OBJECT-TYPE
	SYNTAX		TruthValue
	MAX-ACCESS	read-only
	STATUS		current
	DESCRIPTION	"Indicates whether the current configuration
	    of the Optical Module has been saved. The 
	    cerent15216EdfaOpSaveConfig object can be used to save 
	    the current	configuration." 
	DEFVAL			{ true }
	::=  {  cerent15216EdfaCfgGroup  1  }

cerent15216EdfaLpoutSetpoint	OBJECT-TYPE
	SYNTAX		Integer32  ( 0 .. 1000  )
	MAX-ACCESS	read-only
	STATUS		current
	DESCRIPTION	"Laser pump output power setpoint for
	    the Lpout alarm in units of 0.1mW. This is set when the 
	    attributes cerent15216EdfaPumpCfgConstPumpPower or
	    cerent15216EdfaPumpCfgConstOutPower are set for 
	    pump 2."
	DEFVAL			{ 0 }
	::=  {  cerent15216EdfaCfgGroup  2  }

cerent15216EdfaLpoutDeviation	OBJECT-TYPE
	SYNTAX		Integer32  ( 0 .. 1000  )
	MAX-ACCESS	read-write
	STATUS		current
	DESCRIPTION	"Amount by which the output power must
	    deviate from the setpoint to set the Lpout alarm 
	    in units of 0.01dB. For example a value of 200 is 
            actually 2.00dB" 
	DEFVAL			{ 200 }
	::=  {  cerent15216EdfaCfgGroup  3  }

cerent15216EdfaLpoutHysteresis	OBJECT-TYPE
	SYNTAX		Integer32  ( 0 .. 1000  )
	MAX-ACCESS	read-write
	STATUS		current
	DESCRIPTION	"Amount the output power must move
	    towards the setpoint before the Lpout alarm is 
	    cleared in units of 0.01dB. For example a value
            of 100 is actually 1.00dB" 
	DEFVAL			{ 100 }
	::=  {  cerent15216EdfaCfgGroup  4  }

cerent15216EdfaLOSThreshold	OBJECT-TYPE
	SYNTAX		Integer32  ( -3100 .. -1500  )
	MAX-ACCESS	read-write
	STATUS		current
	DESCRIPTION	"Loss of signal threshold in units of 0.01dBm.
                         For exampe a value of -3000 is actually 
                         -30.0dBm"
	DEFVAL			{ -3000 }
	::=  {  cerent15216EdfaCfgGroup  5  }

cerent15216EdfaLOSHysteresis	OBJECT-TYPE
	SYNTAX		Integer32  ( 0 .. 1000  )
	MAX-ACCESS	read-write
	STATUS		current
	DESCRIPTION	"Amount above cerent15216EdfaLOSThreshold,
	    the input signal must rise before the Lpin alarm is
	    cleared in units of 0.01dB. For example a value of 
            100 is actually 1.0dB"
	DEFVAL			{ 100 }
	::=  {  cerent15216EdfaCfgGroup  6  }

cerent15216EdfaCtmpMin	OBJECT-TYPE
	SYNTAX		Integer32  ( -10 .. 10  )
	MAX-ACCESS	read-write
	STATUS		current
	DESCRIPTION	"Minimum allowable case temperature (C)."
	DEFVAL			{ -5 }
	::=  {  cerent15216EdfaCfgGroup  7  }

cerent15216EdfaCtmpMinHysteresis	OBJECT-TYPE
	SYNTAX		Integer32  ( 0 .. 10  )
	MAX-ACCESS	read-write
	STATUS		current
	DESCRIPTION	"Amount above cerent15216EdfaCtmpMin the
	    case temperature must rise before the Ctmp alarm is 
	    cleared (C)."
	DEFVAL			{ 1 }
	::=  {  cerent15216EdfaCfgGroup  8  }

cerent15216EdfaCtmpMax	OBJECT-TYPE
	SYNTAX		Integer32  ( 20 .. 70  )
	MAX-ACCESS	read-write
	STATUS		current
	DESCRIPTION	"Maximum allowable case temperature (C)."
	DEFVAL			{ 70 }
	::=  {  cerent15216EdfaCfgGroup  9  }

cerent15216EdfaCtmpMaxHysteresis OBJECT-TYPE
	SYNTAX		Integer32  ( 0 .. 10  )
	MAX-ACCESS	read-write
	STATUS		current
	DESCRIPTION	"Amount below cerent15216EdfaCtmpMax the
	    case temperature must drop before the Ctmp alarm is 
	    cleared (C)."
	DEFVAL			{ 1 }
	::=  {  cerent15216EdfaCfgGroup  10  }

cerent15216EdfaCLEI	OBJECT-TYPE
	SYNTAX		Cerent15216EdfaDescr10
	MAX-ACCESS	read-only
	STATUS		current
	DESCRIPTION	"CLEI code."
	::=  {  cerent15216EdfaCfgGroup  11  }

cerent15216EdfaPowerBusMode	OBJECT-TYPE
	SYNTAX		Cerent15216EdfaPowerBusMode
	MAX-ACCESS	read-write
	STATUS		current
	DESCRIPTION	"Power BUS mode"
	DEFVAL 	        { duplex }
	::=  {  cerent15216EdfaCfgGroup 12 }

cerent15216EdfaPowerBusDCVoltageMin	OBJECT-TYPE
	SYNTAX		Cerent15216EdfaPowerBusDCVoltage
	MAX-ACCESS	read-write
	STATUS		current
	DESCRIPTION	"Minimum allowable Power BUS DC voltage is given
                         in units of -0.1V. For example a value of 400 
                         is actually -40.0V"
	DEFVAL 		{ 400 }
	::=  {  cerent15216EdfaCfgGroup 13 }

cerent15216EdfaPowerBusDCVoltageMax	OBJECT-TYPE
	SYNTAX	 	Cerent15216EdfaPowerBusDCVoltage
	MAX-ACCESS	read-write
	STATUS		current
	DESCRIPTION	"Maximum allowable Power BUS DC voltage is given
                         in units of -0.1V. For example a value of 570 
                         is actually -57.0V"
	DEFVAL 		{ 570 }
	::=  {  cerent15216EdfaCfgGroup 14 }

cerent15216EdfaALSMode  OBJECT-TYPE
           SYNTAX       Cerent15216EdfaControl
           MAX-ACCESS   read-write
           STATUS       current
           DESCRIPTION  "Automatic Laser Shutdown. If enabled:
                          - When LOS is detected, the amplifier is shutdown 
                          to 0 mW output power.
                          - When LOS is cleared, the amplifier mode is 
                          restored to the before shutdown state."
           DEFVAL       { disabled }
           ::= { cerent15216EdfaCfgGroup 15 }

-- edfa control

cerent15216EdfaControlCfgGroup	OBJECT-IDENTITY
	STATUS		current
	DESCRIPTION	"Objects relating to the edfa control
	    mode." 
	::=  {  cerent15216EdfaCfg  2  }

-- overall control

cerent15216EdfaOverallControl	OBJECT-IDENTITY
	STATUS		current
	DESCRIPTION	"Objects relating to the overall edfa
			control mode." 
	::=  {  cerent15216EdfaControlCfgGroup  1  }

cerent15216EdfaConstGainOverallGain	OBJECT-TYPE
	SYNTAX		Integer32  ( 130 .. 220 )
	MAX-ACCESS	read-write
	STATUS		current
	DESCRIPTION	"The target overall gain used when control 
                         mode in the PumpCfgTable is set to 
                         constGainTempComp. Given in units of 0.1dB.
                         For example a value of 130 is actually 13.0dB" 
	::=  {  cerent15216EdfaOverallControl  1  }

cerent15216EdfaVariableGainPreAttenuation	OBJECT-TYPE
	SYNTAX		Integer32  ( 10 .. 100  )
	MAX-ACCESS	read-write
	STATUS		current
	DESCRIPTION	"The target pre-attenuation which applies 
                        when the control mode in the PumpCfgTable 
                        is NOT constGainTempComp. Given in units 
                        of 0.1dB. For example a value of 10 is 
                        actually 1.0dB" 
	::=  {  cerent15216EdfaOverallControl  2  }

-- pump cfg table

cerent15216EdfaPumpCfgTable	OBJECT-TYPE
	SYNTAX		SEQUENCE  OF  Cerent15216EdfaPumpCfgEntry
	MAX-ACCESS	not-accessible
	STATUS		current
	DESCRIPTION	"The  Laser Pump Configuration table.
	The table contains two rows - one for each pump.
	Each row contains control mode information for the pump."
	::=  { cerent15216EdfaControlCfgGroup  2 }

cerent15216EdfaPumpCfgEntry	OBJECT-TYPE
	SYNTAX		Cerent15216EdfaPumpCfgEntry
	MAX-ACCESS	not-accessible
	STATUS		current
	DESCRIPTION	"A Laser Pump Configuration table entry." 
	INDEX		{  cerent15216EdfaPumpCfgPumpNum  }
	::=  { cerent15216EdfaPumpCfgTable 1 }

Cerent15216EdfaPumpCfgEntry  ::=  SEQUENCE {
	cerent15216EdfaPumpCfgPumpNum 
	                       Cerent15216EdfaPumpNumber,
	cerent15216EdfaPumpCfgControlMode 
	                       Cerent15216EdfaControlMode,
	cerent15216EdfaPumpCfgConstPumpCurrent	Integer32,
	cerent15216EdfaPumpCfgConstPumpPower  	Integer32,
	cerent15216EdfaPumpCfgConstOutPower  	Integer32
	}

cerent15216EdfaPumpCfgPumpNum	OBJECT-TYPE
	SYNTAX		Cerent15216EdfaPumpNumber
	MAX-ACCESS	not-accessible
	STATUS		current
	DESCRIPTION	"Laser pump number."
	::=  {  cerent15216EdfaPumpCfgEntry  1  }


cerent15216EdfaPumpCfgControlMode	OBJECT-TYPE
	SYNTAX		Cerent15216EdfaControlMode
	MAX-ACCESS	read-write
	STATUS		current
	DESCRIPTION	"Laser pump control mode.
	    When the mode is set directly to (constCurrent, 
	    constPower or constOutputPower), the respective 
	    current value of (ConstPumpCurrent, ConstPumpPower
	    or ConstOutPower) will be used as the constant 
	    parameter for the new mode.

	NOTE: Pump 1 cannot be set to constOutputPower mode."

	DEFVAL { constGainTempComp }
	::=  {  cerent15216EdfaPumpCfgEntry  2  }


cerent15216EdfaPumpCfgConstPumpCurrent	OBJECT-TYPE
	SYNTAX		Integer32  ( 0 .. 300  )
	MAX-ACCESS	read-write
	STATUS		current
	DESCRIPTION	"Laser pump constant pump current (mA).
	    The current used when control mode is changed to 
	    constCurrent." 
	::=  {  cerent15216EdfaPumpCfgEntry  3  }


cerent15216EdfaPumpCfgConstPumpPower	OBJECT-TYPE
	SYNTAX		Integer32  ( 0 .. 100  )
	MAX-ACCESS	read-write
	STATUS		current
	DESCRIPTION	"Laser pump constant pump power (mW).
	    The power used when control mode is changed to 
	    constPower." 
	::=  {  cerent15216EdfaPumpCfgEntry  4  }


cerent15216EdfaPumpCfgConstOutPower	OBJECT-TYPE
	SYNTAX		Integer32  ( 0 .. 650  )
	MAX-ACCESS	read-write
	STATUS		current
	DESCRIPTION	"Laser pump constant output power given in 
                        units of 0.1mW. The power used when control 
                        mode is changed to constOutputPower. For 
                        example a value of 551 is actually 55.1mW" 
	::=  {  cerent15216EdfaPumpCfgEntry  5  }

-- overall status

cerent15216EdfaOverallStatusGroup	OBJECT-IDENTITY
	STATUS	current
	DESCRIPTION	"The overall status of the edfa."
	::=  { cerent15216EdfaStatus  1 }

cerent15216EdfaInPoweruW	OBJECT-TYPE
	SYNTAX		Integer32  ( 0 .. 99999  )
	MAX-ACCESS	read-only
	STATUS		current
	DESCRIPTION	"EDFA input power is given in units of 0.1uW.
                         For example a value of 1353 is actually 135.3uW"
	::=  {  cerent15216EdfaOverallStatusGroup  1  }

cerent15216EdfaInPowerdBm	OBJECT-TYPE
	SYNTAX		Integer32  ( -999999 .. 999999  )
	MAX-ACCESS	read-only
	STATUS		current
	DESCRIPTION	"EDFA input power given in units of 0.01dBm. For
                         example a value of -869 is actually -8.69dBm"
	::=  {  cerent15216EdfaOverallStatusGroup  2  }

cerent15216EdfaOutPowermW	OBJECT-TYPE
	SYNTAX		Integer32  ( 0 .. 999999  )
	MAX-ACCESS	read-only
	STATUS		current
	DESCRIPTION	"EDFA output power given in units of 0.01mW.
                        For example a value of 2148 is actually 21.48mW"
	::=  {  cerent15216EdfaOverallStatusGroup  3  }

cerent15216EdfaOutPowerdBm	OBJECT-TYPE
	SYNTAX		Integer32  ( -99999 .. 99999  )
	MAX-ACCESS	read-only
	STATUS		current
	DESCRIPTION	"EDFA output power given in units of 0.01dBm.
                         For example a value of 1832 is actually 18.32dBm"
	::=  {  cerent15216EdfaOverallStatusGroup  4  }

cerent15216EdfaConstGainOverallGainMeasured  OBJECT-TYPE
	SYNTAX		Integer32  ( 0 .. 230 )
	MAX-ACCESS	read-only
	STATUS		current
	DESCRIPTION	"The measured overall gain used when the
			control mode in the PumpCfgTable is set
			to constGainTempComp. The measured overall 
                        gain is given unit in units of 0.1dB. For 
                        example a value of 219 is actually 21.9dB."
	::=  {  cerent15216EdfaOverallStatusGroup 7  }

cerent15216EdfaVariableGainPreAttenuationMeasured OBJECT-TYPE
	SYNTAX		Integer32  ( 0 .. 110  )
	MAX-ACCESS	read-only
	STATUS		current
	DESCRIPTION	"The measured pre-attenuation given in units
                         of 0.1dB. For example a value of 10 is 
                         actually 1.0dB." 
	::=  {  cerent15216EdfaOverallStatusGroup 8  }

-- pump status table

cerent15216EdfaPumpStatusTable	OBJECT-TYPE
	SYNTAX		SEQUENCE  OF
			    Cerent15216EdfaPumpStatusEntry
	MAX-ACCESS	not-accessible
	STATUS	current
	DESCRIPTION	"The Laser Pump Status table.
	                The table contains two rows - one for each pump.
	                Each row contains the current status information for
	                the pump."
	::=  { cerent15216EdfaStatus  2 }

cerent15216EdfaPumpStatusEntry	OBJECT-TYPE
	SYNTAX		Cerent15216EdfaPumpStatusEntry
	MAX-ACCESS	not-accessible
	STATUS	current
	DESCRIPTION	"A Laser Pump Status table entry."
	INDEX		{  cerent15216EdfaPumpStatusPumpNum  }
	::=  { cerent15216EdfaPumpStatusTable 1 }

Cerent15216EdfaPumpStatusEntry  ::=  SEQUENCE {
	cerent15216EdfaPumpStatusPumpNum
            			Cerent15216EdfaPumpNumber,
	cerent15216EdfaPumpStatusLaserChipTemp  
	                                         Integer32,
	cerent15216EdfaPumpStatusLaserChipTempSetpoint
	                                         Integer32,
	cerent15216EdfaPumpStatusLaserTECCurrent Integer32,
	cerent15216EdfaPumpStatusLaserPower  	 Integer32,
	cerent15216EdfaPumpStatusLaserCurrent    Integer32,
	cerent15216EdfaPumpStatusAmbientTemp  	 Integer32,
	cerent15216EdfaPumpStatusDCVoltage  	 Cerent15216EdfaDCVoltage,
	cerent15216EdfaPumpStatusInPoweruW  	 Integer32,
	cerent15216EdfaPumpStatusInPowerdBm  	 Integer32,
	cerent15216EdfaPumpStatusOutPowermW  	 Integer32,
	cerent15216EdfaPumpStatusOutPowerdBm  	 Integer32,
	cerent15216EdfaPumpStatusGain  		 Integer32,
	cerent15216EdfaPumpStatusControlMode     Cerent15216EdfaControlMode,
        cerent15216EdfaPumpStatusControlValue    
                                            Cerent15216EdfaPumpControlValue
	}


cerent15216EdfaPumpStatusPumpNum	OBJECT-TYPE
	SYNTAX		Cerent15216EdfaPumpNumber
	MAX-ACCESS	not-accessible
	STATUS		current
	DESCRIPTION	"Laser pump number."
	::=  {  cerent15216EdfaPumpStatusEntry  1  }


cerent15216EdfaPumpStatusLaserChipTemp	OBJECT-TYPE
	SYNTAX		Integer32  ( -9999 .. 9999  )
	MAX-ACCESS	read-only
	STATUS		current
	DESCRIPTION	"Laser chip temperature given in units of 0.1C.
                         For example of value of 260 is actually 26.0C"
	::=  {  cerent15216EdfaPumpStatusEntry  2  }


cerent15216EdfaPumpStatusLaserChipTempSetpoint	OBJECT-TYPE
	SYNTAX		Integer32  ( 0 .. 999  )
	MAX-ACCESS	read-only
	STATUS		current
	DESCRIPTION	"Laser chip temperature setpoint given in
                         units of 0.1C. For example a value of 260
                         is actually 26.0C"
	::=  {  cerent15216EdfaPumpStatusEntry  3  }


cerent15216EdfaPumpStatusLaserTECCurrent	OBJECT-TYPE
	SYNTAX		Integer32  ( 0 .. 99999  )
	MAX-ACCESS	read-only
	STATUS		current
	DESCRIPTION	"Laser TEC current (mA)"
	::=  {  cerent15216EdfaPumpStatusEntry  4  }


cerent15216EdfaPumpStatusLaserPower	OBJECT-TYPE
	SYNTAX		Integer32  ( 0 .. 99999  )
	MAX-ACCESS	read-only
	STATUS		current
	DESCRIPTION	"Laser power given in units of 0.01mW. For
                         example a value of 3230 is actually 32.30mW."
	::=  {  cerent15216EdfaPumpStatusEntry  5  }


cerent15216EdfaPumpStatusLaserCurrent	OBJECT-TYPE
	SYNTAX		Integer32  ( 0 .. 999999  )
	MAX-ACCESS	read-only
	STATUS		current
	DESCRIPTION	"Laser current given in units of 0.01mA. For
                         example a value of 4024 is actually 40.24"
	::=  {  cerent15216EdfaPumpStatusEntry  6  }


cerent15216EdfaPumpStatusAmbientTemp	OBJECT-TYPE
	SYNTAX		Integer32  ( -9999 .. 9999  )
	MAX-ACCESS	read-only
	STATUS		current
	DESCRIPTION	"EDFA ambient temperature given in units of 0.01C.
                         For example a value of 2454 is actually 24.54C."
	::=  {  cerent15216EdfaPumpStatusEntry  7  }


cerent15216EdfaPumpStatusDCVoltage	OBJECT-TYPE
	SYNTAX		Cerent15216EdfaDCVoltage
	MAX-ACCESS	read-only
	STATUS		current
	DESCRIPTION	"EDFA DC voltage given in units of 0.1V. For 
                        example a value of 52 is actually 5.2V."
	::=  {  cerent15216EdfaPumpStatusEntry  8  }


cerent15216EdfaPumpStatusInPoweruW	OBJECT-TYPE
	SYNTAX		Integer32  ( 0 .. 99999  )
	MAX-ACCESS	read-only
	STATUS		current
	DESCRIPTION	"This object refers to the optical input power
                         to an EDFA pump. EDFA input power given in units
                         of 0.1uW. For example a value of 1764 is actually
                         176.4uW"
	::=  {  cerent15216EdfaPumpStatusEntry  9  }


cerent15216EdfaPumpStatusInPowerdBm	OBJECT-TYPE
	SYNTAX		Integer32  ( -999999 .. 999999  )
	MAX-ACCESS	read-only
	STATUS		current
	DESCRIPTION	"This object refers to the optical input in dBm 
                         to an EDFA pump. EDFA input power is given in 
                         units of 0.01dBm. For example a value of -753 
                         is actually -7.53"
	::=  {  cerent15216EdfaPumpStatusEntry  10  }


cerent15216EdfaPumpStatusOutPowermW	OBJECT-TYPE
	SYNTAX		Integer32  ( 0 .. 999999  )
	MAX-ACCESS	read-only
	STATUS		current
	DESCRIPTION	"This object refers to the optical output power
                         in mW of an EDFA pummp. EDFA output power is 
                         given in units of 0.01mW. For example a value 
                         of 3497 is actually 34.97mW."
	::=  {  cerent15216EdfaPumpStatusEntry  11  }


cerent15216EdfaPumpStatusOutPowerdBm	OBJECT-TYPE
	SYNTAX		Integer32  ( -99999 .. 99999  )
	MAX-ACCESS	read-only
	STATUS		current
	DESCRIPTION	"This object refers to the optical output power 
                         in dBm of an EDFA pump. EDFA output power is 
                         given in units of 0.01dBm. For example a value
                         of 1542 is actually 15.42dBm."
	::=  {  cerent15216EdfaPumpStatusEntry  12  }


cerent15216EdfaPumpStatusGain	OBJECT-TYPE
	SYNTAX		Integer32  ( -9999 .. 9999  )
	MAX-ACCESS	read-only
	STATUS		current
	DESCRIPTION	"This object refers to the gain across an EDFA
                         pump. EDFA gain is given in units of 0.1dB.
                         For example a value of 229 is actually 22.9dB"
	::=  {  cerent15216EdfaPumpStatusEntry  13 }

cerent15216EdfaPumpStatusControlMode OBJECT-TYPE
    SYNTAX        Cerent15216EdfaControlMode
    MAX-ACCESS    read-only
    STATUS        current
    DESCRIPTION
        "Laser pump control mode."
    ::= { cerent15216EdfaPumpStatusEntry 14 }

cerent15216EdfaPumpStatusControlValue OBJECT-TYPE
    SYNTAX        Cerent15216EdfaPumpControlValue
    MAX-ACCESS    read-only
    STATUS        current
    DESCRIPTION
        "Laser pump control value. Units depend on control mode: 
         For example if the EDFA pump control mode is constGainTempComp
         then a value of 229 is actually 22.9dB."
    ::= { cerent15216EdfaPumpStatusEntry 15 }

-- alarm table

cerent15216EdfaAlarmTable	OBJECT-TYPE
	SYNTAX		SEQUENCE  OF  Cerent15216EdfaAlarmEntry
	MAX-ACCESS	not-accessible
	STATUS	current
	DESCRIPTION	"The current alarms."
	::=  { cerent15216EdfaStatus  3 }

cerent15216EdfaAlarmEntry	OBJECT-TYPE
	SYNTAX		Cerent15216EdfaAlarmEntry
	MAX-ACCESS	not-accessible
	STATUS	current
	DESCRIPTION	"The current alarms."
	INDEX		{  cerent15216EdfaAlarmIndex  }
	::=  { cerent15216EdfaAlarmTable 1 }

Cerent15216EdfaAlarmEntry  ::=  SEQUENCE {
	cerent15216EdfaAlarmIndex  
	                     Cerent15216EdfaIndex,
	cerent15216EdfaAlarmID  
	                     Cerent15216EdfaAlarmID,
	cerent15216EdfaAlarmPriority
	                     Cerent15216EdfaAlarmPriority,
	cerent15216EdfaAlarmState  
	                     Cerent15216EdfaAlarmState,
	cerent15216EdfaAlarmEnableStatus  
	                     Cerent15216EdfaControl,
	cerent15216EdfaAlarmDateAndTime
			     Cerent15216EdfaDateAndTimeString,
	cerent15216EdfaAlarmCfgPriority
	                     Cerent15216EdfaAlarmPriority
	}


cerent15216EdfaAlarmIndex	OBJECT-TYPE
	SYNTAX		Cerent15216EdfaIndex
	MAX-ACCESS	not-accessible
	STATUS		current
	DESCRIPTION	"A unique value to identify this entry."
	::=  {  cerent15216EdfaAlarmEntry  1  }


cerent15216EdfaAlarmID	OBJECT-TYPE
	SYNTAX		Cerent15216EdfaAlarmID
	MAX-ACCESS	read-only
	STATUS		current
	DESCRIPTION	"The alarm this entry refers to."
	::=  {  cerent15216EdfaAlarmEntry  2  }


cerent15216EdfaAlarmPriority	OBJECT-TYPE
	SYNTAX		Cerent15216EdfaAlarmPriority
	MAX-ACCESS	read-only
	STATUS		current
	DESCRIPTION	"The reporting priority of this alarm."
	::=  {  cerent15216EdfaAlarmEntry  4  }


cerent15216EdfaAlarmState	OBJECT-TYPE
	SYNTAX		Cerent15216EdfaAlarmState
	MAX-ACCESS	read-only
	STATUS		current
	DESCRIPTION	"The reporting state of the alarm."
	::=  {  cerent15216EdfaAlarmEntry  5  }


cerent15216EdfaAlarmEnableStatus	OBJECT-TYPE
	   SYNTAX      Cerent15216EdfaControl
	   MAX-ACCESS  read-write
	   STATUS      current
	   DESCRIPTION
	       "If the alarm is enabled/disabled."
	   DEFVAL      { disabled }
	   ::= { cerent15216EdfaAlarmEntry 6 }

cerent15216EdfaAlarmDateAndTime	OBJECT-TYPE
	SYNTAX		Cerent15216EdfaDateAndTimeString
	MAX-ACCESS	read-only
	STATUS		current
	DESCRIPTION	"The local date and time when the alarm
	    entered its current state."
	::=  {  cerent15216EdfaAlarmEntry  9  }

cerent15216EdfaAlarmCfgPriority	OBJECT-TYPE
	SYNTAX		Cerent15216EdfaAlarmPriority
	MAX-ACCESS	read-write
	STATUS		current
	DESCRIPTION	"The configured priority of this alarm."
	::=  {  cerent15216EdfaAlarmEntry  10  }

-- versions

cerent15216EdfaVersionGroup OBJECT-IDENTITY
	STATUS     	current
	DESCRIPTION	"The image version numbers."
	::= { cerent15216EdfaStatus 4 }

cerent15216EdfaCurrentVersion OBJECT-TYPE
	SYNTAX 		DisplayString ( SIZE ( 0 .. 255 ) )
	MAX-ACCESS  	read-only
	STATUS      	current
	DESCRIPTION  	"The version of the currently loaded 
	    image."
	 ::= { cerent15216EdfaVersionGroup 1 }

cerent15216EdfaAlternateVersion OBJECT-TYPE
	SYNTAX DisplayString ( SIZE ( 0 .. 255 ) )
	MAX-ACCESS  read-only
	STATUS      current
	DESCRIPTION "The version of the image to be loaded
	    after a cutover is performed. 

	NOTE:	Derived from cerent15216EdfaBootFileName 1"
	 ::= { cerent15216EdfaVersionGroup 2 }

cerent15216EdfaHardwareVersion OBJECT-TYPE
        SYNTAX DisplayString ( SIZE ( 0 .. 255 ) )
        MAX-ACCESS  read-only
        STATUS      current
        DESCRIPTION
                "The Hardware version of the unit."
         ::= { cerent15216EdfaVersionGroup 3 }

cerent15216EdfaHardwarePartNumber OBJECT-TYPE
        SYNTAX DisplayString ( SIZE ( 0 .. 255 ) )
        MAX-ACCESS  read-only
        STATUS      current
        DESCRIPTION
                "The Hardware Part Number of the unit."
         ::= { cerent15216EdfaVersionGroup 4 }

-- edfa operations

cerent15216EdfaOpGroup	OBJECT-IDENTITY
	STATUS		current
	DESCRIPTION	"Operations on the Edfa
		To perform an operation, the manager sets one of the following
                operations to perform, and provides values to the associated 
                fields:
		    Operation	                 Fields
		    cerent15216EdfaOpSaveConfig  cerent15216EdfaOpRequestId
		    cerent15216EdfaOpCutover	 cerent15216EdfaOpRequestId
		    cerent15216EdfaOpLoad	 cerent15216EdfaOpRequestId
					         cerent15216EdfaOpSrcFileName
					         cerent15216EdfaOpTftpSrvAddr
		    cerent15216EdfaOpReset	 cerent15216EdfaOpRequestId
		    cerent15216EdfaOpDbBackup	 cerent15216EdfaOpRequestId
					         cerent15216EdfaOpDbFileName
		    cerent15216EdfaOpDbRestore	 cerent15216EdfaOpRequestId
					         cerent15216EdfaOpDbFileName
                    
		A cerent15216EdfaOpStarted trap is generated whenever an 
                operation field is set to perform. Only a single operation 
                can be set to perform at any given time.

		To abort the operation the manager sets the 
		Operation field to abort.

		The cerent15216EdfaOpFinished trap will be generated at 
		the completion of the action or if the action is aborted.
                The cerent15216EdfaOpResult attribute indicates if the 
                last operation was successfull."
	::=  {  cerent15216EdfaActions  1  }

cerent15216EdfaOpStatus	OBJECT-TYPE
	SYNTAX		Cerent15216EdfaActionStatus
	MAX-ACCESS	read-only
	STATUS		current
	DESCRIPTION	"The status of the current operation."
	DEFVAL		{ idle }
	::=  {  cerent15216EdfaOpGroup  1  }

cerent15216EdfaOpResult	OBJECT-TYPE
	SYNTAX		Integer32  ( -2147483647 .. 2147483647 )
	MAX-ACCESS	read-only
	STATUS		current
	DESCRIPTION	"This value is used to save the error
			result (if any) of the last operation.
			Success is indicated by a value of 0.

                        For DB backup and restore the following results
                        are possible:

                        0: Success.

                        1: Restore or backup operation cannot obtain the 
                           db semaphore. This error should never occur 
                           because the cerent15216EdfaOpGroup mib 
                           implementation does not allow more than one 
                           operation to be in progress at a time.

                        2: This will occur if there is a problem with 
                           opening cerent15216EdfaOpDbFileName. This could 
                           be because the file system is full, in the 
                           case of a restore the file does not exist, in 
                           the case of a backup the file already exists 
                           on the file system.

                        3: This will occur if the backup procedure cannot
                           obtain a config value.

                        4: This will occur during a restore if the crc in 
                           file specified by cerent15216EdfaOpDbFileName is 
                           not correct, ie corrupted backup file.

                        5: This will occur during a restore if there is a
                           parsing error. This could occur if the backup file
                           was created by a version of software that is not 
                           compatible with the current software version.

                        -1: Unknown internal failure." 
	DEFVAL		{ 0 }
	::=  {  cerent15216EdfaOpGroup  2  }

cerent15216EdfaOpRequestId	OBJECT-TYPE
	SYNTAX		Integer32  ( -2147483647 .. 2147483647 )
	MAX-ACCESS	read-write
	STATUS		current
	DESCRIPTION	"The request identifier for this operation. 
	                This is provided to allow a mananger to match 
			results with actions."
	::=  {  cerent15216EdfaOpGroup  3  }

cerent15216EdfaOpSaveConfig	OBJECT-TYPE
	SYNTAX		Cerent15216EdfaAction
	MAX-ACCESS	read-write
	STATUS		current
	DESCRIPTION	"To save the configuration of the Management &
	                Optical Modules, write 'perform' to this object." 
	DEFVAL		{ idle }
	::=  {  cerent15216EdfaOpGroup  4  }

cerent15216EdfaOpCutover	OBJECT-TYPE
	SYNTAX		Cerent15216EdfaAction
	MAX-ACCESS	read-write
	STATUS		current
	DESCRIPTION	"When 'perform' is written to this
	                object, a cutover will occur where the 
	                cerent15216EdfaAlternateVersion software image will
                	be loaded after a Management Module reset. 

			The cutover operation is achieved automatically by
			swapping cerent15216EdfaBootEntry 1 & 2, then 
			performing a Management Module reset. 

			i.e. the pre-reset cerent15216EdfaAlternateVersion 
			becomes the post-reset cerent15216EdfaCurrentVersion
			and vice-versa."
	DEFVAL 		{ idle }
	::=  {  cerent15216EdfaOpGroup  5  }

cerent15216EdfaOpLoad	OBJECT-TYPE
	SYNTAX		Cerent15216EdfaAction
	MAX-ACCESS	read-write
	STATUS		current
	DESCRIPTION	"When 'perform' is written to this
	                object, a new software image is downloaded via TFTP.

			Before setting this attribute, the source of the 
			new software image should be specified by setting
			cerent15216EdfaOpSrcFileName and 
			cerent15216EdfaOpTftpSrvAddr." 
	DEFVAL	      	{ idle }
	::=  {  cerent15216EdfaOpGroup  6  }

cerent15216EdfaOpSrcFileName	OBJECT-TYPE
	SYNTAX		DisplayString  ( SIZE ( 0 .. 127  ) )
	MAX-ACCESS	read-write
	STATUS		current
	DESCRIPTION	"Source file name for the Load operation.
	                This must include the path of the file relative to 
			the TFTP server's root directory, eg. images/image1."
	::=  {  cerent15216EdfaOpGroup  7  }

cerent15216EdfaOpTftpSrvAddr	OBJECT-TYPE
	SYNTAX		IpAddress
	MAX-ACCESS	read-write
	STATUS		current
	DESCRIPTION	"TFTP file server address for the Load
			operation." 
	DEFVAL		{ '00000000'H }
	::=  {  cerent15216EdfaOpGroup  8  }

cerent15216EdfaOpReset	OBJECT-TYPE
	SYNTAX		Cerent15216EdfaAction
	MAX-ACCESS	read-write
	STATUS		current
	DESCRIPTION	"This object will reset the Management Module and 
	                the Optical Module when the 'perform' value is 
			written to it. The reset will be delayed by
			a short period (approximately 10 seconds) to allow 
			SNMP response to be sent to the manager before the 
			reset is performed."
	DEFVAL		{ idle }
	::=  {  cerent15216EdfaOpGroup  9  }

cerent15216EdfaOpDbFileName	OBJECT-TYPE
	SYNTAX		DisplayString  ( SIZE ( 0 .. 20  ) )
	MAX-ACCESS	read-write
	STATUS		current
	DESCRIPTION	"Db file name for the Db Backup and Db Restore 
                        Operations."
	::=  {  cerent15216EdfaOpGroup  10  }

cerent15216EdfaOpDbBackup OBJECT-TYPE
	SYNTAX		Cerent15216EdfaAction
	MAX-ACCESS	read-write
	STATUS		current
	DESCRIPTION	"When 'perform' is written to this
	                object, the amplifier identification data and 
                        configuration are written to the specified DB backup 
                        file.

			Before setting this attribute, the DB backup file
                        name must specified by setting 
                        cerent15216EdfaDbFileName." 
	DEFVAL	      	{ idle }
	::=  {  cerent15216EdfaOpGroup  11  }

cerent15216EdfaOpDbRestore	OBJECT-TYPE
	SYNTAX		Cerent15216EdfaAction
	MAX-ACCESS	read-write
	STATUS		current
	DESCRIPTION	"When 'perform' is written to this
	                object, the amplifier select configuration 
                        is restored from the specified DB backup 
                        file.

			Before setting this attribute, the DB backup file
                        name must specified by setting 
                        cerent15216EdfaDbFileName." 
	DEFVAL	      	{ idle }
	::=  {  cerent15216EdfaOpGroup  12  }


-- File System Directory table

cerent15216EdfaFfsFileTable  OBJECT-TYPE
	SYNTAX         SEQUENCE OF Cerent15216EdfaFfsFileEntry
	MAX-ACCESS     not-accessible
	STATUS         current
	DESCRIPTION
		"This table contains status information about
		the files within the file system."
	::= { cerent15216EdfaFfsDirectory 1 }

cerent15216EdfaFfsFileEntry    OBJECT-TYPE
	SYNTAX         Cerent15216EdfaFfsFileEntry
	MAX-ACCESS     not-accessible
	STATUS         current
	DESCRIPTION
	     "This file entry."
	INDEX { IMPLIED cerent15216EdfaFfsFileName }
	::= { cerent15216EdfaFfsFileTable  1}

Cerent15216EdfaFfsFileEntry ::= 
	SEQUENCE {
		cerent15216EdfaFfsFileName	     	DisplayString,
		cerent15216EdfaFfsFileType	     	INTEGER,
		cerent15216EdfaFfsFileStatus    	INTEGER,
		cerent15216EdfaFfsFileLength    	Integer32,
		cerent15216EdfaFfsFileAttributes  	Unsigned32
		 }

cerent15216EdfaFfsFileName OBJECT-TYPE
	SYNTAX  DisplayString (SIZE(1..20))
	MAX-ACCESS     not-accessible
	STATUS      current
	DESCRIPTION
		"The name of this file."
	::= { cerent15216EdfaFfsFileEntry 1 }

cerent15216EdfaFfsFileType OBJECT-TYPE
	SYNTAX INTEGER {
			directory(1), 
			sequenced(2),
			record(3),
			unknown(4)
			}
	MAX-ACCESS     read-only
	STATUS      current
	DESCRIPTION
		"The type of this file. sequenced is a normal text file."
	::= { cerent15216EdfaFfsFileEntry 2 }

cerent15216EdfaFfsFileStatus OBJECT-TYPE
	SYNTAX INTEGER {
			deleted(65528),
			ok(65532),
			renameSource(65534), 
			unInitialised(65535)
			}
	MAX-ACCESS  read-only
	STATUS      current
	DESCRIPTION
		"The status of this file."
	::= { cerent15216EdfaFfsFileEntry 3 }
	
cerent15216EdfaFfsFileLength OBJECT-TYPE
	SYNTAX Integer32
	MAX-ACCESS  read-only
	STATUS      current
	DESCRIPTION
		"The length of this file (-1 for 
		cerent15216EdfaFfsFileType = record)."
	::= { cerent15216EdfaFfsFileEntry 4 }
	
cerent15216EdfaFfsFileAttributes OBJECT-TYPE
	SYNTAX Unsigned32 
	MAX-ACCESS  read-only
	STATUS      current
	DESCRIPTION
		"The attributes field for this file."
	::= { cerent15216EdfaFfsFileEntry 5 }

-- File System Operations

cerent15216EdfaFfsOpGroup  OBJECT-IDENTITY
	STATUS     current
	DESCRIPTION
		"The operations that can be performed on the
		of the Flash File System.

		An action may only be started when the value
		of the cerent15216EdfaFileOpStatus field is idle.
	
		To perform an action, the manager sets the 
		attributes as per the following:
		    Operation	                Fields
		    cerent15216EdfaFfsTftpPut  cerent15216EdfaFfsOpOperation
		                                cerent15216EdfaFfsOpRequestId
				                cerent15216EdfaFfsOpSrcName
				                cerent15216EdfaFfsOpDstName
				                cerent15216EdfaFfsOpTftpSrvAddr
		    cerent15216EdfaFileTftpGet	cerent15216EdfaFfsOpOperation
					        cerent15216EdfaFfsOpRequestId
					        cerent15216EdfaFfsOpSrcName
					        cerent15216EdfaFfsOpDstName
					        cerent15216EdfaFfsOpTftpSrvAddr
		    cerent15216EdfaFfsCopy	cerent15216EdfaFfsOpOperation
					        cerent15216EdfaFfsOpRequestId
					        cerent15216EdfaFfsOpSrcName
					        cerent15216EdfaFfsOpDstName
		    cerent15216EdfaFfsRename	cerent15216EdfaFfsOpOperation
					        cerent15216EdfaFfsOpRequestId
					        cerent15216EdfaFfsOpSrcName
					        cerent15216EdfaFfsOpDstName
		    cerent15216EdfaFfsDelete	cerent15216EdfaFfsOpOperation
					        cerent15216EdfaFfsOpRequestId
					        cerent15216EdfaFfsOpSrcName
		    cerent15216EdfaFfsCompress	cerent15216EdfaFfsOpOperation
					        cerent15216EdfaFfsOpRequestId
                    
		The manager then sets the cerent15216EdfaFfsOpAction field
		to perform. This will cause a cerent15216EdfaFfsOpStarted 
                trap to be generated.

		To abort the operation the manager sets the 
		cerent15216EdfaFfsOpAction field to abort.

		The cerent15216EdfaFfsOpFinished trap will be generated at 
		the completion (whether errored or not) of the 
		action."
	::= { cerent15216EdfaFfsActions 1 }

cerent15216EdfaFfsOpAction OBJECT-TYPE
	SYNTAX Cerent15216EdfaAction
	MAX-ACCESS  read-write
	STATUS      current
	DESCRIPTION
		"Start or abort a file operation."
	DEFVAL      { idle }
	::= { cerent15216EdfaFfsOpGroup 1 }

cerent15216EdfaFfsOpOperation OBJECT-TYPE
	SYNTAX INTEGER {cerent15216EdfaFfsNoOperation(1), 
			cerent15216EdfaFfsTftpGet(2),
			cerent15216EdfaFfsTftpPut(3),
			cerent15216EdfaFfsTftpGetRecord(4),
			cerent15216EdfaFfsTftpPutRecord(5),
			cerent15216EdfaFfsCopy(6),
			cerent15216EdfaFfsRename(7),
			cerent15216EdfaFfsCompress(8),
			cerent15216EdfaFfsDelete(9)
		       }

	MAX-ACCESS  read-write
	STATUS      current
	DESCRIPTION
		"Indicates the current (or last) action being 
		performed on this flash file system.

		Note that cerent15216EdfaFfsTftpGet and 
                cerent15216EdfaFfsTftpPut transfer
		normal text or image files."    
	DEFVAL      { cerent15216EdfaFfsNoOperation }
	::= { cerent15216EdfaFfsOpGroup 2 }

cerent15216EdfaFfsOpStatus OBJECT-TYPE
	SYNTAX Cerent15216EdfaActionStatus
	MAX-ACCESS  read-only
	STATUS      current
	DESCRIPTION
		"The status of the operation."
	DEFVAL      { idle }
	::= { cerent15216EdfaFfsOpGroup 3 }

cerent15216EdfaFfsOpStage OBJECT-TYPE
	SYNTAX INTEGER {
			idle(1), 
			flashDirOpen(2), 
			flashDirClose(3), 
			srcFileOpen(4), 
			dstFileOpen(5), 
			srcFileClose(6), 
			dstFileClose(7), 
			readData(8), 
			writeData(9), 
			rename(10), 
			delete(11), 
			findFile(12),
			compress(13),
			nextRecord(14)
			}
	MAX-ACCESS  read-only
	STATUS      current
	DESCRIPTION
		"Indicates the current (or last) stage of the 
		action being performed on this flash file system."
	DEFVAL      { idle }
	::= { cerent15216EdfaFfsOpGroup 4 }

cerent15216EdfaFfsOpCopyProgress OBJECT-TYPE
	SYNTAX INTEGER  (0..99999999) 
	MAX-ACCESS  read-only
	STATUS      current
	DESCRIPTION
		"This provides an indication of the progress
		of the copy operation.

		For normal files this shows bytes copied."
	::= { cerent15216EdfaFfsOpGroup 5 }

cerent15216EdfaFfsOpResult OBJECT-TYPE
	SYNTAX INTEGER (0..999) 
	MAX-ACCESS  read-only
	STATUS      current
	DESCRIPTION
		"Indicates the result of the last operation.
		Success is indicated by a value of 0."
	::= { cerent15216EdfaFfsOpGroup 6 }

cerent15216EdfaFfsOpRequestId OBJECT-TYPE
	SYNTAX INTEGER (0..999) 
	MAX-ACCESS  read-write
	STATUS      current
	DESCRIPTION
		"The request identifier for this operation.

		 This is provided to allow manangers to match
		 actions and results."
	::= { cerent15216EdfaFfsOpGroup 7 }

cerent15216EdfaFfsOpSrcName OBJECT-TYPE
	SYNTAX DisplayString (SIZE(0..127)) 
	MAX-ACCESS  read-write
	STATUS      current
	DESCRIPTION
		"Source file name for the operation.

		Note that Flash File names are limited
		to 20 bytes, the longer name is provided
		support long path names for TFTP 
		operations from servers."
	::= { cerent15216EdfaFfsOpGroup 8 }

cerent15216EdfaFfsOpDstName OBJECT-TYPE
	SYNTAX DisplayString (SIZE(0..127)) 
	MAX-ACCESS  read-write
	STATUS      current
	DESCRIPTION
		"Destination file name for the operation

		Note that Flash File names are limited
		to 20 bytes, the longer name is provided
		support long path names for TFTP 
		operations to servers."
	::= { cerent15216EdfaFfsOpGroup 9 }

cerent15216EdfaFfsOpTftpSrvAddr OBJECT-TYPE
	SYNTAX IpAddress
	MAX-ACCESS  read-write
	STATUS      current
	DESCRIPTION
		"TFTP file server address."
	DEFVAL      { '00000000'H }
	::= { cerent15216EdfaFfsOpGroup 10 }

--
-- Notifications 
--

cerent15216EdfaOpFinished	NOTIFICATION-TYPE
	OBJECTS		{ cerent15216EdfaOpSaveConfig ,
			  cerent15216EdfaOpCutover ,
			  cerent15216EdfaOpLoad ,
			  cerent15216EdfaOpSrcFileName ,
			  cerent15216EdfaOpTftpSrvAddr ,
			  cerent15216EdfaOpReset ,
			  cerent15216EdfaOpResult ,
			  cerent15216EdfaOpRequestId,
                          cerent15216EdfaOpDbFileName,
                          cerent15216EdfaOpDbBackup,
                          cerent15216EdfaOpDbRestore  }
	STATUS		current
	DESCRIPTION	" Op Finished.
	    This trap indicates that an operation has 
	    completed."
	::=  {  cerent15216EdfaEventsV2  1  }

cerent15216EdfaAlarmActivated	NOTIFICATION-TYPE
	OBJECTS		{ cerent15216EdfaAlarmID ,
	                  cerent15216EdfaAlarmPriority ,
			  cerent15216EdfaAlarmDateAndTime  }
	STATUS		current
	DESCRIPTION	"Alarm Activated.
	    A notification indicating an alarm has changed to an 
	    active state."
	::=  {  cerent15216EdfaEventsV2  2  }

cerent15216EdfaAlarmCleared	NOTIFICATION-TYPE
	OBJECTS		{ cerent15216EdfaAlarmID ,
	                  cerent15216EdfaAlarmPriority ,
			  cerent15216EdfaAlarmDateAndTime  }
	STATUS		current
	DESCRIPTION	"Alarm Cleared.
	    A notification indicating an alarm has changed to a 
	    cleared state." 
	::=  {  cerent15216EdfaEventsV2  3  }

cerent15216EdfaFfsOpFinished NOTIFICATION-TYPE
	OBJECTS { cerent15216EdfaFfsOpOperation, 
                  cerent15216EdfaFfsOpStage,
                  cerent15216EdfaFfsOpCopyProgress,
		  cerent15216EdfaFfsOpResult, 
		  cerent15216EdfaFfsOpRequestId,
		  cerent15216EdfaFfsOpSrcName,
		  cerent15216EdfaFfsOpDstName,
	          cerent15216EdfaFfsOpTftpSrvAddr }
	 STATUS  current
	 DESCRIPTION
		"File System Op Finished.
		This trap indicates that the file
		operation has completed or aborted."
	 ::= { cerent15216EdfaEventsV2 4 }

cerent15216EdfaFfsOpStarted NOTIFICATION-TYPE
	OBJECTS { cerent15216EdfaFfsOpOperation, 
		  cerent15216EdfaFfsOpRequestId,
		  cerent15216EdfaFfsOpSrcName,
		  cerent15216EdfaFfsOpDstName,
	          cerent15216EdfaFfsOpTftpSrvAddr }
	 STATUS  current
	 DESCRIPTION
		"File System Op has started.
		This trap indicates that the file
		operation has started."
	 ::= { cerent15216EdfaEventsV2 5 }

cerent15216EdfaOpStarted  NOTIFICATION-TYPE
	OBJECTS		{ cerent15216EdfaOpSaveConfig,
			  cerent15216EdfaOpCutover,
			  cerent15216EdfaOpLoad,
			  cerent15216EdfaOpSrcFileName,
			  cerent15216EdfaOpTftpSrvAddr,
			  cerent15216EdfaOpReset,
			  cerent15216EdfaOpRequestId,
                          cerent15216EdfaOpDbFileName,
                          cerent15216EdfaOpDbBackup,
                          cerent15216EdfaOpDbRestore  }
	STATUS		current
	DESCRIPTION	" Op Started.
	    This trap indicates that an operation has 
	    started."
	::=  {  cerent15216EdfaEventsV2  6  }

END
