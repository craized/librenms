-- **************************************************************
-- File name: cerentGeneric.mib
-- Module name: Cerent-GENERIC-MIB module
--
-- This module contains the generic objects and generic events 
-- for the Cisco ONS Network Element ONS 15327, 15310 .

-- Copyright (c) 1998-1999 by Cerent Corporation, Inc.
-- Copyright (c) 1999-2004 by Cisco Systems, Inc.
-- All rights reserved.
--
-- **************************************************************

CERENT-GENERIC-MIB DEFINITIONS ::= BEGIN

IMPORTS
    MODULE-IDENTITY,
    OBJECT-TYPE,
    OBJECT-IDENTITY,
    NOTIFICATION-TYPE,
    Integer32,
    Unsigned32,
    Counter32
                      FROM SNMPv2-SMI
    TEXTUAL-CONVENTION,
    DisplayString, 
    TruthValue,
    TimeStamp
                      FROM SNMPv2-TC
    MODULE-COMPLIANCE, 
    OBJECT-GROUP, 
    NOTIFICATION-GROUP 
                      FROM SNMPv2-CONF
    cerentGeneric,
    cerentRequirements,
    cerentModules
                      FROM CERENT-GLOBAL-REGISTRY
    CerentNotificationClass,
    CerentAlarmSeverity,
    CerentAlarmStatus,
    CerentAlarmServiceAffecting,
    CerentMonitorType,
    CerentLocation,
    CerentPeriod,
    CerentPortNumber
                      FROM CERENT-TC;

cerentGenericMibModule MODULE-IDENTITY
    LAST-UPDATED "0410010000Z" -- 2004/Oct/01
    ORGANIZATION "Cisco Systems, Inc."
    CONTACT-INFO
        "         support@Cisco.com

         Postal:  Cisco Systems
                  1450 N. McDowell Blvd.
                  Petaluma, CA  94954
                  USA

            Tel:  +1-877-323-7368"
    DESCRIPTION
        "This module provides the definitions for 
         generic objects and notifications of 
         Cisco ONS network device, ONS 15327, 15310."

    REVISION "0410010000Z" -- 2004/Oct/01
    DESCRIPTION
         "This file can be used with R5.0 release."

    ::= { cerentModules 40 }

cerentConformance OBJECT-IDENTITY
      STATUS      current
      DESCRIPTION
            "This node is created for compliance. Has 
             objects as required by the RFCs"
      ::= { cerentRequirements 10 }

--  ********************************************************

cerentGenericGroups OBJECT-IDENTITY
      STATUS      current
      DESCRIPTION
            "All the objects and events are
             grouped under this for conformance"
      ::= { cerentConformance 10 }

cerentCompliance OBJECT-IDENTITY
      STATUS      current
      DESCRIPTION
            "The compliance statements
             for Cisco ONS 15327, 15310."
      ::= { cerentConformance 20 }

-- **************************************************************
-- Cisco ONS generic textual conventions
-- **************************************************************

CerentGenericAlarmType ::= TEXTUAL-CONVENTION
--   DISPLAY-HINT "d"
   STATUS current
   DESCRIPTION
       "This TC is used by the NMS to map the alarm type
        received by the trap and and display the string
        shown in LHS."
   SYNTAX INTEGER {
       alarmUnknown                                       (  1 ), 
       alarmCutoffIsInManualMode                         ( 10 ), 
       failureDetectedExternalToTheNE                    ( 20 ),
       externalError                                     ( 30 ), 
       excessiveSwitching                                ( 40 ), 
       sdccTerminationFailure                            ( 50 ), 
       incomingFailureCondition                          ( 60 ), 
       alarmIndicationSignal                             ( 70 ), 
       alarmIndicationSignalLine                         ( 80 ), 
       alarmIndicationSignalPath                         ( 90 ), 
       alarmIndicationSignalVT                           ( 100 ),
       apsChannelFailure                                 ( 110 ), 
       channelByteFailureAPS                             ( 120 ), 
       channelProtectionSwitchingChannelMatchFailureAPS  ( 130 ), 
       channelAutomaticProtectionSwitchModeMismatchAPS   ( 140 ), 
       farEndProtectionLineFailure                       ( 150 ), 
       inconsistentAPSCode                               ( 160 ), 
       improperAPSCode                                   ( 170 ), 
       nodeIdMismatch                                    ( 180 ), 
       channelDefaultKAPS                                ( 190 ), 
       connectionLoss                                    ( 200 ), 

       bipolarViolation                                  ( 210 ), 
       carrierLossOnTheLAN                               ( 220 ), 
       concatenationErrorSTS                             ( 230 ), 
       excessCollisionsOnTheLAN                          ( 240 ), 
       facilityFailure                                   ( 250 ), 
       farEndAIS                                         ( 260 ), 
       farEndMultipleDS1LOSDetectedOnDS3                 ( 270 ), 
       farEndDS1EqptFailNonServiceAffecting              ( 280 ), 
       farEndDS1EqptFailServiceAffecting                 ( 290 ), 
       farEndSingleDS1LOS                                ( 300 ), 
       farEndDS3EqptFailNonServiceAffecting              ( 310 ), 
       farEndDS3EqptFailServiceAffecting                 ( 320 ), 
       farEndCommonEquipmentFailureNonServiceAffecting   ( 330 ), 
       farEndIDLE                                        ( 340 ), 
       farEndLOS                                         ( 350 ), 
       farEndLOF                                         ( 360 ), 
       farEndBlockError                                  ( 370 ), 
       ds3IdleCondition                                  ( 380 ), 
       lossOfFrame                                       ( 390 ), 
       lossOfPointer                                     ( 400 ), 

       lossOfPointerPath                                 ( 410 ), 
       lossOfPointerVT                                   ( 420 ), 
       lossOfSignal                                      ( 430 ), 
       outOfFrame                                        ( 440 ), 
       pathSelectorFailure                               ( 450 ), 
       remoteAlarmIndication                             ( 460 ), 
       remoteFailureIndication                           ( 470 ), 
       remoteFailureIndicationLine                       ( 480 ), 
       remoteFailureIndicationPath                       ( 490 ), 
       remoteFailureIndicationVT                         ( 500 ), 

       signalDegrade					 ( 510 ), 
       severelyErroredFrame                              ( 520 ), 
       signalFailure					 ( 530 ), 
       signalLabelMismatchFailure                  ( 540 ), 
       payloadDefectIndication                           ( 550 ), 

       payloadDefectIndicationPath                            ( 560 ), 
       payloadLabelMismatchPath                               ( 570 ), 
       signalLabelMismatchFailurePayloadLabelMismatchVT       ( 580 ), 
       unequippedPath                                         ( 590 ), 
       signalLabelMismatchFailureUnequippedVT                 ( 600 ), 
       lossOfSynchronization                                  ( 610 ), 
       outOfSynchronization                                   ( 620 ), 
       primarySynchronizationReferenceFailure                 ( 630 ), 
       secondarySynchronizationReferenceFailure               ( 640 ), 
       thirdSynchronizationReferenceFailure                   ( 650 ), 
       fourthSynchronizationReferenceFailure                  ( 660 ), 
       fifthSynchronizationReferenceFailure                   ( 670 ), 
       sixthSynchronizationReferenceFailure                   ( 680 ), 

       failedToReceiveSynchronizationStatusMessage             ( 690 ),
       synchronizationStatusMessagesAreDisabledOnThisInterface ( 700 ),
       stratum1PrimaryReferenceSourceTraceable                 ( 710 ),
       synchronizedTraceabilityUnknown                         ( 720 ),
       stratum2Traceable                                       ( 730 ),
       transitNodeClockTraceable                               ( 740 ),

       stratum3ETraceable                    ( 750 ),
       stratum3Traceable                     ( 760 ),
       sonetMinimumClockTraceable            ( 770 ),
       stratum4Traceable                     ( 780 ),
       doNotUseForSynchronization            ( 790 ),
       reservedForNetworkSynchronizationUse  ( 800 ),

       outgoingFailureCondition          ( 810 ), 
       remoteDefectIndicationLine        ( 820 ), 
       remoteDefectIndicationPath        ( 830 ), 
       freeRunningSynchronizationMode    ( 840 ), 
       holdoverSynchronizationMode       ( 850 ), 
       fastStartSynchronizationMode      ( 860 ), 
       internalFault                     ( 870 ), 
       internalError                     ( 880 ), 
       internalMessageError              ( 890 ), 
       mismatchOfEquipmentAndAttributes  ( 900 ), 
       watchdogTimerTimeout              ( 910 ), 
       softwareFaultOrFailure            ( 920 ), 
       softwareFaultDataIntegrityFault   ( 930 ), 
       programFailure                    ( 940 ), 

       controlEquipmentFailure                                 ( 950 ), 
       primaryNonVolatileBackupMemoryFailure                   ( 960 ), 
       secondaryNonVolatileBackupMemoryFailure                 ( 970 ), 
       controlBusFailure                                       ( 980 ), 
       controlBus1Failure                                      ( 990 ), 
       controlBus2Failure                                     ( 1000 ),

       tccAToShelfSlot1DROP1CommunicationFailure        ( 1010 ),
       tccAToShelfSlot2DROP2CommunicationFailure        ( 1020 ),
       tccAToShelfSlot3DROP3CommunicationFailure        ( 1030 ),
       tccAToShelfSlot4DROP4CommunicationFailure        ( 1040 ),
       tccAToShelfSlot5TRUNK1CommunicationFailure       ( 1050 ),
       tccAToShelfSlot6TRUNK2CommunicationFailure       ( 1060 ),
       tccAToShelfSlot7TCCACommunicationFailure         ( 1070 ),
       tccAToShelfSlot8XCONACommunicationFailure        ( 1080 ),
       tccAToShelfSlot9AICCommunicationFailure          ( 1090 ),
       tccAToShelfSlot10XCONBCommunicationFailure       ( 1100 ),
       tccAToShelfSlot11TCCBCommunicationFailure        ( 1110 ),
       tccAToShelfSlot12TRUNK3CommunicationFailure      ( 1120 ),
       tccAToShelfSlot13TRUNK4CommunicationFailure      ( 1130 ),
       tccAToShelfSlot14DROP5CommunicationFailure       ( 1140 ),
       tccAToShelfSlot15DROP6CommunicationFailure       ( 1150 ),
       tccAToShelfSlot16DROP7CommunicationFailure       ( 1160 ),
       tccAToShelfSlot17DROP8CommunicationFailure       ( 1170 ),
       tccAToDCCAProcessorCommunicationFailure          ( 1180 ),
       tccBToShelfSlot1DROP1CommunicationFailure        ( 1190 ),
       tccBToShelfSlot2DROP2CommunicationFailure        ( 1200 ),
       tccBToShelfSlot3DROP3CommunicationFailure        ( 1210 ),
       tccBToShelfSlot4DROP4CommunicationFailure        ( 1220 ),
       tccBToShelfSlot5TRUNK1CommunicationFailure       ( 1230 ),
       tccBToShelfSlot6TRUNK2CommunicationFailure       ( 1240 ),
       tccBToShelfSlot7TCCACommunicationFailure         ( 1250 ),
       tccBToShelfSlot8XCONACommunicationFailure        ( 1260 ),
       tccBToShelfSlot9AICCommunicationFailure          ( 1270 ),
       tccBToShelfSlot10XCONBCommunicationFailure       ( 1280 ),
       tccBToShelfSlot11TCCBCommunicationFailure        ( 1290 ),
       tccBToShelfSlot12TRUNK3CommunicationFailure      ( 1300 ),
       tccBToShelfSlot13TRUNK4CommunicationFailure      ( 1310 ),
       tccBToShelfSlot14DROP5CommunicationFailure       ( 1320 ),
       tccBToShelfSlot15DROP6CommunicationFailure       ( 1330 ),
       tccBToShelfSlot16DROP7CommunicationFailure       ( 1340 ),
       tccBToShelfSlot17DROP8CommunicationFailure       ( 1350 ),
       tccBToDCCBProcessorCommunicationFailure          ( 1360 ),

       controlEquipmentControlCommunicationsEquipmentFailure ( 1370 ),
       controlProcessorFailure                               ( 1380 ),
       workingMemoryFailure                                  ( 1390 ),

       interconnectionEquipmentFailure                     ( 1400 ),
       payloadBusFailureToIOSlot1XCONSlot8                  ( 1410 ),
       payloadBusFailureToIOSlot2XCONSlot8                  ( 1420 ),
       payloadBusFailureToIOSlot3XCONSlot8                  ( 1430 ),
       payloadBusFailureToIOSlot4XCONSlot8                  ( 1440 ),
       payloadBusFailureToIOSlot5XCONSlot8                  ( 1450 ),
       payloadBusFailureToIOSlot6XCONSlot8                  ( 1460 ),
       payloadBusFailureToIOSlot12XCONSlot8                 ( 1470 ),
       payloadBusFailureToIOSlot13XCONSlot8                 ( 1480 ),
       payloadBusFailureToIOSlot14XCONSlot8                 ( 1490 ),
       payloadBusFailureToIOSlot15XCONSlot8                ( 1500 ),
       payloadBusFailureToIOSlot16XCONSlot8                ( 1510 ),
       payloadBusFailureToIOSlot17XCONSlot8                ( 1520 ),
       payloadBusFailureToIOSlot1XCONSlot10                ( 1530 ),
       payloadBusFailureToIOSlot2XCONSlot10                ( 1540 ),
       payloadBusFailureToIOSlot3XCONSlot10                ( 1550 ),
       payloadBusFailureToIOSlot4XCONSlot10                ( 1560 ),
       payloadBusFailureToIOSlot5XCONSlot10                ( 1570 ),
       payloadBusFailureToIOSlot6XCONSlot10                ( 1580 ),
       payloadBusFailureToIOSlot12XCONSlot10               ( 1590 ),
       payloadBusFailureToIOSlot13XCONSlot10               ( 1600 ),
       payloadBusFailureToIOSlot14XCONSlot10               ( 1610 ),
       payloadBusFailureToIOSlot15XCONSlot10               ( 1620 ),
       payloadBusFailureToIOSlot16XCONSlot10               ( 1630 ),
       payloadBusFailureToIOSlot17XCONSlot10               ( 1640 ),
       timeSlotInterchangeEquipmentFailure                 ( 1650 ),

       equipmentFailure                                    ( 1660 ),
       highTemperature                                     ( 1670 ),
       invalidMACAddress                                   ( 1680 ),
       boardFailure                                        ( 1690 ),
       diagnosticFailure                                   ( 1700 ),
       mediumAccessControlFailure                          ( 1710 ),
       facilityTerminationEquipmentFailure                 ( 1720 ),
       automaticLaserShutoffDueToHighTemperature           ( 1730 ),
       failureToReleaseFromProtection                      ( 1740 ),
       receiverFailure                                     ( 1750 ),
       transmitFailure                                     ( 1760 ),
       facilityTerminationEquipmentReceiverMissing         ( 1770 ),
       facilityTerminationEquipmentTransmitterMissing      ( 1780 ),
       failureToSwitchToProtection                         ( 1790 ),
       failureToSwitchToProtectionRing                     ( 1800 ),

       failureToSwitchToProtectionSpan                     ( 1810 ),
       failureToSwitchToProtectionPath                     ( 1820 ),
       fanFailure                                          ( 1830 ),
       equipmentUnitPlugIn                                 ( 1840 ),
       nePowerFailureAtConnector                           ( 1850 ),
       fuseAlarm                                           ( 1860 ),
       synchronizationUnitFailure                          ( 1870 ),
       synchronizationSwitchingEquipmentFailure            ( 1880 ),
       equipmentUnitUnplugged                              ( 1890 ),
       loopback                                            ( 1900 ),

       ds1LoopbackDueToFEACCommand                         ( 1910 ),
       loopbackCommandSentToFarEndDS1                      ( 1920 ),
       ds3LoopbackDueToFEACCommand                         ( 1930 ),
       ds3LoopbackCommandSentToFarEnd                      ( 1940 ),
       ds2LoopbackDueToFarEndCommand                       ( 1950 ),
       ds2LoopbackCommandSentToFarEnd                      ( 1960 ),
       facilityLoopback                                    ( 1970 ),
       networkLoopback                                     ( 1980 ),
       terminalLoopback                                    ( 1990 ),
       manuallyCausedAbnormalCondition                     ( 2000 ),
       ethernetBridgeIsNewRootOfSpanningTree               ( 2010 ),
       ethernetBridgeTopologyChange                        ( 2020 ),
       normalCondition                                     ( 2030 ),
       embeddedOperationsChannelFailureLinkDown            ( 2040 ),
       peerStateMismatch                                   ( 2050 ),
       proceduralError                                     ( 2060 ),
       improperRemoval                                     ( 2070 ),
       duplicateNodeID                                     ( 2080 ),
       blsrOutOfSync                                       ( 2090 ),
       blsrMultiNodeTableUpdateCompleted                   ( 2100 ),
       protectionUnitNotAvailable                          ( 2110 ),
       performanceMonitorThresholdCrossingAlert            ( 2120 ),
       protectionSwitch                                    ( 2130 ),
       recoveryOrServiceProtectionActionHasBeenInitiated   ( 2140 ),
       automaticSystemReset                                ( 2150 ),
       automaticUPSRSwitchCausedByAIS          ( 2160 ),
       automaticUPSRSwitchCausedByLOP          ( 2170 ),
       automaticUPSRSwitchCausedByUNEQ         ( 2180 ),
       automaticUPSRSwitchCausedByPDI          ( 2190 ),
       automaticUPSRSwitchCausedBySFBER        ( 2200 ),
       automaticUPSRSwitchCausedBySDBER        ( 2210 ),
       coldRestart                              ( 2220 ),
       forcedSwitchBackToWorking( 2230 ),
       forcedSwitchBackToWorkingRing                     ( 2240 ),
       forcedSwitchBackToWorkingSpan                     ( 2250 ),
       forcedSwitchToProtection                          ( 2260 ),

       forcedSwitchToProtectionRing                          ( 2270 ),
       forcedSwitchToProtectionSpan                          ( 2280 ),
       workingFacilityOrEquipmentForcedToSwitchToProtectionPath( 2290 ),

       initializationInitiated   ( 2300 ),
       lockoutOfProtection       ( 2310 ),
       lockoutOfProtectionRing   ( 2320 ),
       lockoutOfProtectionSpan   ( 2330 ),
       lockoutOfProtectionPath   ( 2340 ),
       lockoutOfWorking          ( 2350 ),
       lockoutOfWorkingRing      ( 2360 ),
       lockoutOfWorkingSpan      ( 2370 ),

       manualSystemReset         ( 2380 ),

       manualSwitchToInternalClock                   ( 2390 ),
       manualSwitchToPrimaryReference                ( 2400 ),
       manualSwitchToSecondReference                 ( 2410 ),
       manualSwitchToThirdReference                  ( 2420 ),
       manualSwitchToFourthReference                 ( 2430 ),
       manualSwitchToFifthReference                  ( 2440 ),
       manualSwitchToSixthReference                  ( 2450 ),

       manualSwitchBackToWorking                             ( 2460 ),
       manualSwitchBackToWorkingRing                         ( 2470 ),
       manualSwitchBackToWorkingSpan                         ( 2480 ),
       manualSwitchToProtection                              ( 2490 ),
       manualSwitchToProtectionRing                          ( 2500 ),
       manualSwitchToProtectionSpan                          ( 2510 ),
       manualSwitchOfWorkingFacilityOrEquipmentToProtectionPath ( 2520 ),

       powerfailRestart           ( 2530 ),
       ringIsSquelchingTraffic    ( 2540 ),
       softwareDownloadInProgress ( 2550 ),

       switchToInternalClock   ( 2560 ),
       switchToPrimaryReference               ( 2570 ),
       switchToSecondReference                ( 2580 ),
       switchToThirdReference                 ( 2590 ),
       switchToFourthReference                ( 2600 ),
       switchToFifthReference                 ( 2610 ),
       switchToSixthReference                 ( 2620 ),

       systemReboot                                        ( 2630 ),
       switchedBackToWorking                               ( 2640 ),
       switchedToProtection                                ( 2650 ),
       warmRestart                                         ( 2660 ),
       ringIsInWaitToRestoreState                          ( 2670 ),
       manualSwitchRequest            ( 2680 ),
       forcedSwitchRequest             ( 2690 ),
       lockoutSwitchRequest           ( 2700 ),
       rmonHistoriesAndAlarmsResetReboot                ( 2710 ),
       rmonThresholdCrossingAlarm                 ( 2720 ),
       alarmsSuppressedByUserCommand             ( 2730 ),
       alarmsSuppressedForMaintenance             ( 2740 ),
       switchingMatrixModuleFailure             ( 2750 ),
       lanConnectionPolarityReversed             ( 2760 ),
       autonomousPMReportMessageInhibited           ( 2780 ),
       ioSlotToXCONCommunicationFailure             ( 2790 ),

         -- Intentional gap

       stsPathTraceIdentifierMismatch             ( 2800 ),
       nePowerFailureAtConnectorA                 ( 2810 ),
       nePowerFailureAtConnectorB                 ( 2820 ),

       freeMemoryOnCardVeryLow                    ( 2830 ),
       freeMemoryOnCardNearZero                   ( 2840 ),

       exerciseRequestOnRing                      ( 2850 ),
       exerciseRequestOnSpan                      ( 2860 ),
       squelchingPath                             ( 2870 ),
       extraTrafficPreempted                      ( 2880 ),

       farEndLockoutOfWorkingRing                 ( 2890 ),
       farEndLockoutOfWorkingSpan                 ( 2900 ),
       farEndLockoutOfProtectionRing              ( 2910 ),
       farEndLockoutOfProtectionAllSpans          ( 2920 ),

       farEndWorkingFacilityForcedToSwitchToProtectionRing     ( 2930 ),
       farEndWorkingFacilityForcedToSwitchToProtectionSpan     ( 2940 ),

       farEndManualSwitchOfWorkingFacilityToProtectionRing     ( 2950 ),
       farEndManualSwitchOfWorkingFacilityToProtectionSpan     ( 2960 ),
       farEndExercisingRing                                    ( 2970 ),
       farEndExercisingSpan                                    ( 2980 ),
       farEndBERThresholdPassedForSignalFailureRing ( 2990 ),
       farEndBERThresholdPassedForSignalFailureSpan ( 3000 ),
       farEndBERThresholdPassedForSignalDegradeRing ( 3010 ),
       farEndBERThresholdPassedForSignalDegradeSpan ( 3020 ),
       apsChannelFarEndProtectionLineSignalDegrade  ( 3030 ),

       ringSwitchIsActiveOnTheEastSide      ( 3040 ),
       ringSwitchIsActiveOnTheWestSide      ( 3050 ),
       spanSwitchIsActiveOnTheEastSide      ( 3060 ),
       spanSwitchIsActiveOnTheWestSide      ( 3070 ),

       uniDirectionalFullPassThroughIsActive  ( 3080 ),
       biDirectionalFullPassThroughIsActive   ( 3090 ),

       kBytesPassThroughIsActive       ( 3100 ),
       ringIsSegmented                 ( 3110 ),
       ringTopologyIsUnderConstruction ( 3120 ),

       lockoutOfProtectionAllSpans                   ( 3130 ),
       farEndOfFiberIsProvisionedWithDifferentRingID ( 3140 ),
       bothEndsOfFiberProvisionedAsEastOrBothAsWest  ( 3150 ),
       securityInvalidLoginUsernameSeeAuditTrail     ( 3160 ),

       autonomousMessagesInhibited        ( 3170 ),
       trafficStormOnLANLANTemporarilyDisabled( 3180 ),

       reptdbchgMessagesInhibited    ( 3190 ),
       securityUserIDHasExpired      ( 3200 ),
       partialFanFailure             ( 3210 ),
       forcedSwitchRequestOnRing     ( 3220 ),
       forcedSwitchRequestOnSpan     ( 3230 ),
       lockoutSwitchRequestOnRing    ( 3240 ),
       lockoutSwitchRequestOnSpan    ( 3250 ),
       manualSwitchRequestOnRing     ( 3260 ),
       manualSwitchRequestOnSpan     ( 3270 ),

       communicationFailurePeerToPeerSlotControlBusA ( 3280 ),
       communicationFailurePeerToPeerSlotControlBusB ( 3290 ),
       controllerAToShelfSlotCommunicationFailure ( 3300 ),
       controllerBToShelfSlotCommunicationFailure ( 3310 ),

       interconnectionEquipmentFailureWorkingPayloadBus ( 3320 ),
       interconnectionEquipmentFailureProtectPayloadBus ( 3330 ),
       inhibitSwitchToProtectRequestOnEquipment ( 3340 ),
       inhibitSwitchToWorkingRequestOnEquipment ( 3350 ),

       berThresholdExceededForSignalDegradeLine ( 3360 ),
       berThresholdExceededForSignalDegradePath ( 3370 ),
       berThresholdExceededForSignalFailureLine ( 3380 ),
       berThresholdExceededForSignalFailurePath ( 3390 ),
       exercisingRingSuccessfully               ( 3400 ),
       exercisingSpanSuccessfully               ( 3410 ),
       spanIsInWaitToRestoreState        ( 3420 ),
       exerciseRequestOnRingFailed            ( 3430 ),
       exerciseRequestOnSpanFailed            ( 3440 ),
       farEndLockoutOfProtectionSpan          ( 3450 ),

       manufacturingDataMemoryEEPROMFailure   ( 3460 ),
       replaceableEquipmentOrUnitIsMissing    ( 3470 ),
       softwareDownloadFailed                 ( 3480 ),
       extraTrafficPCADropped                 ( 3490 ),

       etherTxOversubscribed          ( 3500 ),
       etherRxOverSubscribed          ( 3510 ),
       etherTxExcessFlowCtrl          ( 3520 ),
       etherRxExcessFlowCtrl          ( 3530 ),
       transportLayerFailure          ( 3540 ),
       etherTxUnderrun                ( 3550 ),

       synchronizationReferenceFrequencyOutOfBounds  ( 3560 ),
       ntpOrSntpHostFailure                          ( 3570 ),
       peerCardNotResponding                         ( 3580 ),
       alarmsAndEventsSuppressedForThisObject        ( 3590 ),
       ds3FrameFormatMismatch                        ( 3600 ),

       waitToRestore             ( 3610 ),
       extremeHighVoltBatteryA   ( 3620 ),
       extremeLowVoltBatteryA    ( 3630 ),
       extremeHighVoltBatteryB   ( 3640 ),
       extremeLowVoltBatteryB    ( 3650 ),
       iosConfigCopyFailed             ( 3660 ),
       iosConfigCopyInProgress             ( 3670 ),

       signalingUnableToSetupCircuit        ( 3710 ),
       errorInStartupConfig             ( 3712 ),
       noStartupConfig             ( 3714 ),
       needToSaveRunningConfig             ( 3716 ),
       invalidAlarm             ( 3718 ),
       rsvpHelloFSMToNeighborDown ( 3720 ),
       securityInvalidLoginUsername     ( 3722 ),
       databaseBackupFailed             ( 3724 ),
       databaseRestoreFailed             ( 3726 ),
       lmpHelloFSMToControlChannelDown   ( 3730 ),
       lmpNeighborDiscoveryHasFailed        ( 3740 ),
       unauthorizedIncomingSignalingRequest ( 3750 ),
       auditLog80PercentFull             ( 3760 ),
       moduleCommunicationFailure             ( 3762 ),
       auditLog100PercentFullOldestRecordsWillBeLost             ( 3764 ),
       standbyDatabaseOutOfSync             ( 3766 ),
       redundantPowerCapabilityLost             ( 3768 ),
       forcedSwitchToPrimaryReference       ( 3770 ),
       forcedSwitchToSecondReference             ( 3780 ),
       forcedSwitchToThirdReference             ( 3790 ),
       forcedSwitchToInternalClock             ( 3800 ),
       industrialHighTemperature             ( 3805 ),
       improperMatrixEquipmentInserted               ( 3810 ),
       eqptProblemOnCarrierOrPIM                     ( 3820 ),
       eqptProblemOnPIMOrPPM                         ( 3830 ),
       timSectionTraceIdentifierMismatchFailure    ( 4000 ),
       aisMultiplexSectionAlarmIndicationSignal      ( 4010 ),
       rfiMultiplexSectionRemoteFailureOrAlarmIndication( 4020 ),
       timHighOrderTraceIdentifierMismatchFailure    ( 4030 ),
       aisAdministrationUnitAlarmIndicationSignal    ( 4040 ),
       lopAdministrationUnitLossOfPointer            ( 4050 ),
       slmfUnequippedHighOrderPathUnequipped         ( 4060 ),
       slmfPLMHighOrderPathLabelMismatch             ( 4070 ),
       rfiHighOrderRemoteFailureOrAlarmIndication    ( 4080 ),
       lopTributaryUnitLossOfPointer                 ( 4090 ),
       aisTributaryUnitAlarmIndicationSignal         ( 4100 ),
       slmfUnequippedLowOrderPathUnequipped          ( 4110 ),
       slmfPLMLowOrderPathLabelMismatch              ( 4120 ),
       timLowOrderTraceIdentifierMismatchFailure     ( 4130 ),
       rfiLowOrderRemoteFailureOrAlarmIndication     ( 4140 ),
       g811PrimaryReferenceClockTraceable            ( 4150 ),
       g812TransitNodeClockTraceable                 ( 4160 ),
       g812LocalNodeClockTraceable                   ( 4170 ),
       g813SynchronousEquipmentTimingSourceTraceable ( 4180 ),
       e1LoopbackDueToFEACCommand                    ( 4190 ),
       e1LoopbackCommandSentToFarEnd                 ( 4200 ),
       e3LoopbackDueToFEACCommand                    ( 4210 ),
       farEndMultipleE1LOSDetectedOnE3               ( 4220 ),
       farEndE1EqptFailNonServiceAffecting           ( 4230 ),
       farEndE1EqptFailServiceAffecting              ( 4240 ),
       farEndSingleE1LOS                             ( 4250 ),
       farEndE3EqptFailServiceAffecting              ( 4260 ),
       e3LoopbackCommandSentToFarEnd                 ( 4270 ),
       farEndE3EqptFailNonServiceAffecting           ( 4280 ),
       lowVoltBatteryA                               ( 4290 ),
       highVoltBatteryA                              ( 4300 ),
       lowVoltBatteryB                               ( 4310 ),
       highVoltBatteryB                              ( 4320 ),
       msspRingOutOfSync                             ( 4330 ),
       msspMultiNodeTableUpdateCompleted             ( 4340 ),
       automaticSNCPSwitchCausedByAIS                ( 4350 ),
       automaticSNCPSwitchCausedByLOP                ( 4360 ),
       automaticSNCPSwitchCausedByUNEQ               ( 4370 ),
       automaticSNCPSwitchCausedByPDI                ( 4380 ),
       automaticSNCPSwitchCausedBySFBER              ( 4390 ),
       automaticSNCPSwitchCausedBySDBER              ( 4400 ),
       stmConcatenationError                         ( 4410 ),
       e3IdleCondition                               ( 4420 ),
       channelMSSPInconsistentAPSCode                ( 4430 ),
       channelMSSPImproperAPSCodeAPS                 ( 4440 ),
       channelMSSPNodeIdMismatchAPS                  ( 4450 ),
       channelMSSPDefaultKAPS                        ( 4460 ),
       channelMSSPConnectionLossAPS                  ( 4470 ),
       minimumClockTraceableSDH                      ( 4480 ),
       lineIsInWaitToRestoreStateSDH                 ( 4490 ),
       berThresholdExceededForSignalDegradeHighOrder ( 4500 ),
       berThresholdExceededForSignalFailureHighOrder ( 4510 ),
       berThresholdExceededForSignalDegradeLowOrder  ( 4520 ),
       berThresholdExceededForSignalFailureLowOrder  ( 4530 ),
       failureToSwitchToProtectionHighOrderPath      ( 4540 ),
       failureToSwitchToProtectionLowOrderPath       ( 4550 ),
       lofAdministrationUnitLossOfMultiFrame         ( 4560 ),
       sdhSpanIsInWaitToRestoreState                 ( 4570 ),
       a8b10bOutOfSync                               ( 4755 ),
       odukPMAlarmIndicationSignal                   ( 4760 ),
       otukAlarmIndicationSignal                     ( 4765 ),
       otukSMBackwardDefectIndication                ( 4770 ),
       fecUncorrectedWord                            ( 4780 ),
       gccTerminationFailure                         ( 4785 ),
       otukIncomingAlignmentError                    ( 4790 ),
       odukLockedDefectPM                            ( 4795 ),
       lossOfMultiFrame                              ( 4800 ),
       odukOpenConnectionIndication                  ( 4805 ),
       payloadTypeIdentifierMismatch                 ( 4810 ),
       odukTrailTraceIdentifierMismatch              ( 4815 ),
       otukTrailTraceIdentifierMismatch              ( 4820 ),
       equipmentHighLaserBias                        ( 4825 ),
       equipmentHighLaserTemp                        ( 4830 ),
       equipmentHighLaserPeltier                     ( 4835 ),
       equipmentHighRxPower                          ( 4840 ),
       equipmentHighTxPower                          ( 4845 ),
       equipmentHighTransceiverVoltage               ( 4850 ),
       equipmentLowLaserBias                         ( 4855 ),
       equipmentLowLaserTemp                         ( 4860 ),
       equipmentLowLaserPeltier                      ( 4865 ),
       equipmentLowRxPower                           ( 4870 ),
       equipmentLowTxPower                           ( 4875 ),
       equipmentLowTransceiverVoltage                ( 4880 ),
       equipmentRxLocked                             ( 4885 ),
       equipmentSquelched                            ( 4890 ),
       equipmentTxLocked                             ( 4895 ),
       otukSignalFailure                              ( 4900 ),
       odukSignalFailure                              ( 4905 ),
       otukSignalDegrade                              ( 4910 ),
       odukSignalDegrade                              ( 4915 ),
       pluggablePortMissing                          ( 4920 ),
       pluggablePortRateMismatch                     ( 4925 ),
       pluggablePortSecurityCodeMismatch             ( 4930 ),
       tciNotSelected                                ( 4935 ),
       tci1ClockFailure                              ( 4940 ),
       odukPMBackwardDefectIndication                 ( 4945 ),
       odukTCM1BackwardDefectIndication               ( 4950 ),
       odukTCM2BackwardDefectIndication               ( 4955 ),
       equipmentHighRxTemperature                    ( 4960 ),
       equipmentLowRxTemperature                     ( 4965 ),
       tci2ClockFailure                              ( 4970 ),
       equipmentWavelengthMismatch                   ( 4975 ),
       dspCommunicationFailure                       ( 4980 ),
       dspFailure                                    ( 4985 ),
       laserApproachingEndOfLife                     ( 5000 ),
       crossconnectLoopback                          ( 5010 ),
       adminLogoutOfUser                             ( 5020 ),
       userLockedOut                                 ( 5030 ),
       adminLockoutOfUser                            ( 5040 ),
       adminLockoutClear                             ( 5050 ),
       invalidLoginUsername                          ( 5060 ),
       securityInvalidLoginPassword                  ( 5070 ),
       securityInvalidLoginLockedOut                 ( 5080 ),
       securityInvalidLoginAlreadyLoggedOn           ( 5090 ),
       loginOfUser                                   ( 5100 ),
       automaticLogoutOfIdleUser                     ( 5110 ),
       logoutOfUser                                  ( 5120 ),
       enhancedRemoteFailureIndicationPathServer     ( 5200 ),
       enhancedRemoteFailureIndicationPathConnectivity( 5210 ),
       enhancedRemoteFailureIndicationPathPayload    ( 5220 ),
       firewallHasBeenDisabled                       ( 5230 ),
       securityIntrusionDetPwd                       ( 5240 ),
       securityIntrusionDetUser                      ( 5250 ),
       connectionEquipmentMismatch                   ( 5260 ),
       disableInactiveUser                           ( 5270 ),
       disableInactiveClear                          ( 5280 ),
       batteryFailure                                ( 5290 ),

       extremeHighVolt                               ( 5300 ),
       extremeLowVolt                                ( 5310 ),
       highVolt                                      ( 5320 ),
       lowVolt                                       ( 5330 ),
       suspendUser                                   ( 5340 ), 
       suspendUserClear                              ( 5350 ),
       lineDccTerminationFailure                     ( 5360 ),
       multiplexSectionDccTerminationFailure         ( 5370 ),
       gigaBitEthernetOutOfSync                      ( 5380 ),
       sequenceMismatch                              ( 5390 ),
       lossOfAlignment                               ( 5400 ),
       outOfUseByAdministrativeCommand               ( 5410 ),
       outOfUseTransportFailure                      ( 5420 ),
       vcatGroupDown                                 ( 5430 ),
       vcatGroupDegraded                             ( 5440 ),
       vcatGroupIncomplete                           ( 5450 ),
       alarmIndicationSignalInTX                     ( 5460 ),
       remoteAlarmIndicationInTX                     ( 5470 ),
       kByteAPSChannelFailure                        ( 5480 ),
       apsInvalidMode                                ( 5490 ),
       ipAddressAlreadyInUseWithinTheSameDccArea     ( 5500 ),
       nodeNameInUseWithinTheSameDccArea             ( 5510 ),
       rearPanelEthernetLinkRemoved                  ( 5520 ),
       manualSwitchToProtectResultedInNoTrafficSwitch      ( 5530 ),
       manualSwitchBackToWorkingResultedInNoTrafficSwitch  ( 5540 ),
       forcedSwitchToProtectResultedInNoTrafficSwitch      ( 5550 ),
       forcedSwitchBackToWorkingResultedInNoTrafficSwitch  ( 5560 ),
       duplicateSerialNumberDetectedOnAPluggableEntity     ( 5570 ),
       lossOfSignalForOpticalChannel                       ( 5600 ),
       encapsulationMismatchPath                           ( 5610 ),
       encapsulationMismatchVT             ( 5620 ),
       encapsulationMismatchHighOrderPath             ( 5630 ),
       encapsulationMismatchLowOrderPath             ( 5640 ),
       gfpUserPayloadMismatch                              ( 5650 ),
       gfpFibreChannelDistanceExtensionMismatch            ( 5660 ),
       gfpFibreChannelDistanceExtensionBufferStarvation    ( 5670 ),
       gfpFibreChannelDistanceExtensionCreditStarvation    ( 5680 ),
       automaticWdmAnsFinished                             ( 5690 ),
       gfpClientSignalFailDetected                         ( 5700 ),
       gfpLossOfFrameDelineation                           ( 5710 ),
       gfpExtensionHeaderMismatch                          ( 5730 ),
       incomingOverheadSignalAbsent                  ( 5740 ),
       opticalSafetyRemoteInterlockOn                ( 5750 ),
       automaticPowerControlCorrectionSkipped        ( 5770 ),
       apcCannotSetValueDueToRangeLimits             ( 5780 ),
       lcasVcgMemberTxSideInAddState                 ( 5790 ),
       farEndManualSwitchBackToWorkingSpan             ( 5800 ),
       farEndForcedSwitchBackToWorkingSpan             ( 5810 ),
       universalTransponderModuleHardwareFailure             ( 5820 ),
       universalTransponderModuleCommunicationFailure             ( 5830 ),
       pluginModuleRangeSettingsMismatch             ( 5840 ),
       lcasVcgMemberTxSideInDnuState                 ( 5850 ),
       lcasControlWordCrcCheckFailure            ( 5860 ),
       lcasVcgMemberRxSideInFailState            ( 5870 ),
       signalLossOnDataInterface             ( 5880 ),
       synchronizationLossOnDataInterface             ( 5890 ),
       portFAIL               ( 5900 ),
       unreachablePortTargetPower               ( 5910 ),
       portAddPowerDegradeLow               ( 5920 ),
       portAddPowerDegradeHigh             ( 5930 ),
       portAddPowerFailLow             ( 5940 ),
       portAddPowerFailHigh             ( 5950 ),
       automaticPowerControlTerminatedOnManualRequest             ( 6000 ),
       oduk1AlarmIndicationSignal             ( 6010 ),
       oduk2AlarmIndicationSignal             ( 6020 ),
       oduk3AlarmIndicationSignal             ( 6030 ),
       oduk4AlarmIndicationSignal             ( 6040 ),
       temperatureReadingMismatchBetweenSCCards             ( 6050 ),
       voltageReadingMismatchBetweenSCCards             ( 6060 ),
       alarmsSuppressedonOutOfGroupVcatMember           ( 6070 ),
       blsrSoftwareVersionMismatch             ( 6080 ),
       optimized1Plus1ApsPrimaryFacility       ( 6090 ),
       optimized1Plus1ApsPrimarySectionMismatch( 6100 ),
       optimized1Plus1ApsInvalidPrimarySection ( 6110 ),
       compositeClockHighLineVoltage             ( 6120 ),
       berThresholdExceededForSignalDegradeVt             ( 6130 ),
       berThresholdExceededForSignalFailureVt             ( 6140 ),
       spanLengthOutOfRange             ( 6150 ),
       idleSignalCondition             ( 6170 ),
       idleSignalConditionInTx             ( 6180 ),
       vtPathTraceIdentifierMismatch             ( 6190 ),
       lossOfFrameInTX             ( 6200 ),
       provisioningMismatch             ( 6210 ),
       sectionTraceIdentifierMismatch             ( 6220 ),
       regeneratorSectionTraceIdentifierMismatch             ( 6230 ),
       switchingMatrixModuleFailureWorking             ( 6240 ),
       switchingMatrixModuleFailureProtect             ( 6250 ),
       slotCommunicationDisabled             ( 6260 ),
       sessionTimeLimitExpired             ( 6270 ),
       userPasswordChangeRequired             ( 6280 ),
       isisAdjacencyFailure             ( 6290 ),
       msspSoftwareVersionMismatch             ( 6300 ),
       remoteAuthenticationFailSeeAuditLog             ( 6310 ),
       illegalRouteAdditionToNetwork             ( 6320 ),
       ringIsSquelchingStsTraffic            ( 6330 ),
       ringIsSquelchingVtTraffic             ( 6340 ),
       archiveOfAuditLogFailed               ( 6350 ),
       rprWrapped             ( 6360 ),
       shelfCommunicationFailure             ( 6370 ),
       duplicatedShelfIdentifier             ( 6380 ),
       softwareMismatch             ( 6390 ),
       lmpFailure             ( 6400 ),
       opticalTerminationIncomplete             ( 6410 ),
       forwardDefectIndication             ( 6420 ),
       payloadMissingIndication             ( 6430 ),
       spanMeasurementCannotBePerformed     ( 6440 ),
       ringIsSquelchingHighOrderTraffic             ( 6450 ),
       ringIsSquelchingLowOrderTraffic             ( 6460 ),
       badPacketCountExceedsThreshold             ( 6470 ),
       linkLayerKeepAliveFailure             ( 6480 ),
       autonegotiationRemoteFailureIndication             ( 6490 ),
       trailSignalFail             ( 6500 ),
       ds1LoopbackCommandSentToFarEnd             ( 6510 ),
       multiplexSectionSignalDegraded             ( 6520 ),
       multiplexSectionExcessiveErrors             ( 6530 ),
       highOrderPathSignalDegraded             ( 6540 ),
       highOrderPathExcessiveErrors             ( 6550 ),
       lowOrderPathSignalDegraded             ( 6560 ),
       lowOrderPathExcessiveErrors             ( 6570 ),
       regeneratorSectionDccTerminationFailure ( 6580 ),
       networkMemoryPoolLow             ( 6590 ),
       ospfRoutingTableOverflow             ( 6600 ),
       autoLaserShutdownDisabled             ( 6610 ),
       wavelengthOutOfLock                           ( 6620 ),
       rprProtectionIsActive             ( 6630 ),
       maxRPRStationNumberExceeded             ( 6640 ),
       rprProtectionConfigurationMismatched             ( 6650 ),
       reservedBandwidthLinkRateExceededOnRinglet0             ( 6660 ),
       reservedBandwidthLinkRateExceededOnRinglet1             ( 6670 ),
       rprInterfaceInPassThroughMode             ( 6680 ),
       rprPeerNodeIsMissing             ( 6690 ),
       rprRiFailure                 ( 6700 ),
       rprSignalFailure             ( 6710 ),
       rprSignalDegrade             ( 6720 ),
       interlinkFailure             ( 6730 ),
       apcWrongGain             ( 6740 ),
       rprSpanMismatch             ( 6750 ),
       fastAutomaticProtectionSwitching             ( 6840 ),
       fastAutomaticProtectionSwitchingConfigMismatch             ( 6850 ),
       lcasSinkGroupError             ( 6860 ),
       lcasVCGMemberRxSideInDNUState             ( 6870 ),
       fcDistanceExtFuncNotEstablished             ( 6880 ),
       nonCiscoPPMInserted             ( 6890 ),
       unqualifiedPPMInserted             ( 6900 ),
       ftaMismatch             ( 6910 ),
       cardPortsUnableToProvideProtection             ( 6920 ),
       lmpSignalDegrade             ( 6930 ),
       lmpSignalFailure             ( 6940 ),
       lmpUnallocatedDataLink             ( 6950 ),
       frontPortLinkLoss             ( 6960 ),
       bertEnabled             ( 6970 ),
       bertSynchronizationStatusFailed             ( 6975 ),
       workQueueFull             ( 6980 ),
       equipmentPowerFailureAtConnectorA             ( 7000 ),
       equipmentPowerFailureAtConnectorB             ( 7005 ),
       equipmentPowerFailureAtReturnConnectorA       ( 7010 ),
       equipmentPowerFailureAtReturnConnectorB       ( 7015 ),
       loginFailThresholdExceeded                    ( 7020 ),
       connectionIdMismatchOnMatrixA                 ( 7025 ),
       connectionIdMismatchOnMatrixB                 ( 7030 ),
       manufacturingEepromFailure		     ( 7035 ),
       equipmentFailureHighTemperature               ( 7040 ),
       laserBiasCurrentHigh                          ( 7045 ),
       highLaserTemperature                          ( 7050 ),
       bridgeAndRollHasOccurred                      ( 7055 ),
       bridgeAndRollIsPendingAValidSignal            ( 7060 ),
       airFlow                                       ( 7065 ),
       partialFanFailurePartsFailure                 ( 7070 ),
       unprotectedSyncronizationEquipment            ( 7075 ),
       unprotectedMatrixEquipment                    ( 7080 ),
       matrixEquipmentUnavailable                    ( 7085 ),
       controlBusFailureTscA                         ( 7090 ),
       controlBusFailureTscB                         ( 7095 ),
       payloadBusFailureMatrixA                      ( 7100 ),
       payloadBusFailureMatrixB                      ( 7105 ),
       matrixOperationSuspended                      ( 7110 ),
       clockFailureTsc                               ( 7115 ),
       payloadLoopback				     ( 7120 ),
       dccChannelLoss                                ( 7125 ),
       reptPmMsgInhibited                            ( 7130 ),
       loopbackCrs                                   ( 7135 ),
       syncRefFreqOutOfBound                         ( 7140 ),
       systemUpgradeInProgress                       ( 7145 ),
       eqptFailToBoot                                ( 7150 ),
       eqptPowerFailure                              ( 7155 ),
       clockBusFailureTscA                           ( 7160 ),
       clockBusFailureTscB                           ( 7165 ),
       powerFuseFailure                              ( 7170 ),
       controlCommunicationsEquipmentFailure         ( 7175 ),
       differentSoftwareVersion                      ( 7180 ),
       ospfHelloFail                                 ( 7185 ),
       clockModuleFrequencyMismatch                  ( 7190 ),
       etherPortSwitch                               ( 7195 ),
       openIOSlots                                   ( 7200 ),
       equipmentBootInProgress                       ( 7205 ),
       lossOfClockFromMateShelfController	     ( 7210 ),
       dcuLossFailure             ( 7230 ),
       ochncMaintenance             ( 7235 ),
	   alarmIndicationSignalInTXCustomerInstallation (7435),
	   remoteAlarmIndicationInTXCustomerInstallation (7440),
       odukTCM1AlarmIndicationSignal                 ( 13100 ),
       odukTCM2AlarmIndicationSignal                 ( 13105 ),
       odukLockedDefectTCM1                          ( 13110 ),
       odukLockedDefectTCM2                          ( 13115 ),
       otukLossOfFrame                               ( 13120 ),
       odukOpenConnectionIndicationTCM1		     ( 13125 ),
       odukOpenConnectionIndicationTCM2		     ( 13130 ),
       odukTrailTraceIdentifierMismatchTCM1          ( 13135 ),
       odukTrailTraceIdentifierMismatchTCM2          ( 13140 ),
       odukSignalFailureTCM1                         ( 13145 ),
       odukSignalFailureTCM2                         ( 13150 ),
       odukSignalDegradeTCM1                         ( 13155 ),
       odukSignalDegradeTCM2                         ( 13160 ),
       lossOfChannel                                 ( 13165 ),
       fecMismatch                                   ( 13170 ),
       timSectionMonitorTraceIdentifierMismatchFailure ( 13175 ),
       automaticLaserShutdown                        ( 13180 ),
       shutterInsertionLossVariationDegradeLow       ( 13200 ),
       opticalChannelDeactivationFailure             ( 13205 ),
       shutterInsertionLossVariationDegradeHigh      ( 13210 ),
       networkTopologyIncomplete                     ( 13215 ),
       pluginModuleCommunicationFailure              ( 13220 ),
       opticalNetworkTypeMismatch                    ( 13225 ),
       opticalPowerDegradeLow                        ( 13230 ),
       automaticPowerControlFailure                  ( 13235 ),
       opticalPowerDegradeHigh                       ( 13240 ),
       automaticPowerControlDisabled                 ( 13245 ),
       opticalPowerFailureLow                        ( 13250 ),
       ringIdMismatch                                ( 13255 ),
       opticalPowerFailureHigh                       ( 13260 ),
       lossOfContinuity                              ( 13270 ),
       variableOpticalAttenuatorDegradeLow           ( 13280 ),
       variableOpticalAttenuatorDegradeHigh          ( 13290 ),
       variableOpticalAttenuatorFailureLow           ( 13300 ),
       variableOpticalAttenuatorFailureHigh          ( 13310 ),
       laserBiasDegrade                              ( 13320 ),
       laserBiasFailure                              ( 13330 ),
       laserTemperatureDegrade                       ( 13340 ),
       opticalAmplifierGainDegradeLow                ( 13350 ),
       opticalAmplifierGainDegradeHigh               ( 13360 ),
       opticalAmplifierGainFailureLow                ( 13370 ),
       opticalAmplifierGainFailureHigh               ( 13380 ),
       opticalChannelConnectionFailure               ( 13390 ),
       opticalChannelIncomplete                      ( 13395 ),
       opticalChannelActivationFailure               ( 13400 ),
       laserAutoPowerReduction                       ( 13410 ),
       caseTemperatureDegrade                        ( 13420 ),
       fiberTemperatureDegrade                       ( 13430 ),
       shutterOpen                                   ( 13440 ),
       awgTemperatureDegrade                         ( 13450 ),
       awgTemperatureFailure                         ( 13460 ),
       awgOverTemperature                            ( 13470 ),
       opticalAmplifierInitialization                ( 13480 ),
       awgWarmUp                                     ( 13490 ),
       incSigloss                                    ( 13510 ),
       incSyncloss                                   ( 13515 ),
       incGfpOutOfFrame                              ( 13520 ),
       incGfpSigLoss                                 ( 13525 ),
       incGfpSyncLoss                                ( 13530 )
} 

CerentGenericEntityClass ::= TEXTUAL-CONVENTION
--   DISPLAY-HINT "d"
   STATUS current
   DESCRIPTION
       "This is the TC used to find out to which cerentGenericEntityClass
        an alarm belongs to."
   SYNTAX INTEGER {
  unknownEntity   (  1 ),
  ne              ( 10 ),
  backplane       ( 30 ),
  eqpt            ( 50 ),
  port            ( 60 ),
  ocn             ( 70 ),
  stmn            ( 71 ),
  aip             ( 80 ),
  fanTray         ( 90 ),
  crs             ( 100 ),
  ds3             ( 110 ),
  almExpPanel     ( 120 ),
  almIfExtnsn     ( 130 ),
  stsMon          ( 140 ),
  vcMonHp         ( 141 ),
  dwdmClient      ( 150 ),
  stsTerm         ( 160 ),
  vcTermHp        ( 161 ),
  dwdmTrunk       ( 170 ),
  dwdmOptics      ( 180 ),
  psSts           ( 190 ),
  rsms            ( 200 ),
  xcSts           ( 210 ),
  bits            ( 220 ),
  dwdmFec         ( 230 ),
  neSynchRef      ( 240 ),
  dwdm8b10b       ( 250 ),
  extSynchRef     ( 260 ),
  dwdmOtn         ( 270 ),
  envAlrm         ( 280 ),
  envCtrl         ( 290 ),
  neRing          ( 360 ),
  ds1             ( 390 ),
  vtMon           ( 410 ),
  vcMonLp         ( 411 ),
  vtTerm          ( 420 ),
  vcTermLP        ( 421 ),
  fUdc            ( 430 ),
  msUdc           ( 440 ),
  spareSdcc       ( 450 ),
  ucpCircuit      ( 480 ),
  ucpIpcc         ( 490 ),
  ucpNeighbor     ( 500 ),
  ec1             ( 510 ),
  ps              ( 520 ),
  psVt            ( 530 ),
  e100t           ( 540 ),
  e1000t          ( 550 ),
  etherBridge     ( 560 ),
  e1              ( 600 ),
  e3              ( 630 ),
  e4              ( 640 ),
  stm1E           ( 650 ),
  ds3i            ( 660 ),
  g1000           ( 670 ),
  ml100t          ( 680 ),
  ml1000          ( 690 ),
  dwdmSfp         ( 700 ),
  dwdmScl         ( 710 ),
  dwdmTcm1        ( 720 ),
  dwdmTcm2        ( 730 ),
  dwdmOcn         ( 740 ),
  dwdmSm          ( 750 ),
  dwdmPm          ( 760 ),
  dwdmTcm         ( 770 ),
  pwr             ( 780 ),
  stsTermVcat     ( 790 ),
  vtTermVcat      ( 800 ),
  vcatGroup       ( 810 ),
  fcmr            ( 820 ),
  entOptics       ( 830 ),
  ce100t          ( 840 ),
  ppm             ( 850 ),
  twor            ( 860 ),
  isc             ( 870 ),
  escon           ( 880 ),
  bic             ( 890 ),
  gfp             ( 900 ),
  gige            ( 910 ),
  pos             ( 920 ),
  cap             ( 930 ),
  dwdmData        ( 940 ),
  logFac          ( 950 ),
  ge              ( 960 ),
  fc              ( 970 ),
  ec1p1           ( 980 ),
  mlFx            ( 990 ),
  ochTerm          ( 1000 ),
  shelf          ( 1010 ),
  ce1000          ( 1020 ),
  cemr           ( 1030 ),
  lmp          ( 1040 ),
  lmpControlChannel          ( 1050 ),
  lmpTeLink          ( 1060 ),
  lmpDataLink          ( 1070 ),
  rpr          ( 1080 ),
  ether          ( 1090 ),
  mlmr          ( 1100 ),
  otu2          ( 1110 ),
  aots           ( 3200 ),
  ots            ( 3210 ),
  oms            ( 3220 ),
  och            ( 3230 ),
  osc            ( 3240 ),
  ochc           ( 3250 )

}

-- **************************************************************
cerentGenericObjects OBJECT-IDENTITY
      STATUS      current
      DESCRIPTION
            "All the generic objects definitions are grouped
             under this" 
      ::= { cerentGeneric 10 }

-- **************************************************************

cerentGenericCommonObjectsGroup OBJECT-IDENTITY
      STATUS      current
      DESCRIPTION
            "The group to combine all the Cisco OTBU common 
             objects" 
      ::= { cerentGenericObjects 10 }

cerentGenericEnableNotification   OBJECT-TYPE
       SYNTAX      TruthValue
       MAX-ACCESS  read-write
       STATUS      current
       DESCRIPTION
               "This variable indicates whether the system produces
                notifications.  A value=FALSE will prevent notifications
                from being sent by this system."
       DEFVAL { true }
       ::= { cerentGenericCommonObjectsGroup 10 }

cerentGenericNodeTime OBJECT-TYPE
       SYNTAX       DisplayString 
       MAX-ACCESS   read-only
       STATUS current
       DESCRIPTION
       "Indicates current local time as reflected by
        the Cisco OTBU equipment. The format this scalar is
        YYYYMMDDhhmmss{S/D}. E.g., 
        20011103133453D means 1:34:53 PM PDT on 03/Nov/2001
        19990614095436S means 9:54:36 AM PST on 14/Jun/1999.
        If the last octet is S then the time is standard time.
        Otherwise it is D to indicate it is daylight saving
        time, if applicable"
       ::= { cerentGenericCommonObjectsGroup 20 }

cerentGenericSentNotifications OBJECT-TYPE  
       SYNTAX      Counter32 
       MAX-ACCESS read-only
       STATUS current
       DESCRIPTION
              "A count of v1+v2 notifications sent out
               by the agent. Resets to zero after
               cold/warm start."
       ::= { cerentGenericCommonObjectsGroup 30 }

cerentGenericLastChangeTime OBJECT-TYPE
    SYNTAX      TimeStamp
    MAX-ACCESS  read-only
    STATUS      current
    DESCRIPTION
            "The value of sysUpTime at the time 
             a conceptual row is created or deleted 
             in cerentGenericAlarmTable "
    ::= { cerentGenericCommonObjectsGroup 40 }

cerentGenericMultishelfEnabled   OBJECT-TYPE
    SYNTAX      TruthValue
    MAX-ACCESS  read-only
    STATUS      current
    DESCRIPTION
    "This variable indicates whether the system is configured
     in multi-shelf mode or single-shelf mode."
    DEFVAL { false }
    ::= { cerentGenericCommonObjectsGroup 50 }

-- **************************************************************
-- 
cerentGenericGeneralGroup OBJECT-IDENTITY
       STATUS       current
       DESCRIPTION
              "Another class of objects found in
               Cisco ONS 15327, 15310 "
       ::= { cerentGenericObjects 20 }

cerentGenericSoftwareVersion OBJECT-TYPE
       SYNTAX       DisplayString
       MAX-ACCESS   read-only
       STATUS current
       DESCRIPTION
       "Indicates the version of software that is
        used in Cisco ONS Network element, 
        ONS 15327, 15310. E.g., 2.2.03"
       ::= { cerentGenericGeneralGroup 10 }

cerentGenericAlarmGroup OBJECT-IDENTITY
       STATUS       current
       DESCRIPTION
              "The group that will represent all the
               alarm info in the Cisco ONS network element, 
               ONS 15327, 15310"
       ::= { cerentGenericObjects 30 }

cerentGenericAlarmCount       OBJECT-TYPE
       SYNTAX       Unsigned32
       MAX-ACCESS   read-only
       STATUS current
       DESCRIPTION
           "Total number of active alarms in the 
            Cisco ONS network element, ONS 15327, 15310.
            This equals the total number of rows in
            cerentGenericAlarmTable at any time."
       ::= { cerentGenericAlarmGroup 10 }

cerentGenericAlarmTable       OBJECT-TYPE
       SYNTAX SEQUENCE OF CerentGenericAlarmEntry
       MAX-ACCESS not-accessible 
       STATUS current
       DESCRIPTION
               "This table has all currently raised conditions
                for the network node. A Condition is a fault or
                status detected by hardware or software."
       ::= { cerentGenericAlarmGroup 20 }

cerentGenericAlarmEntry       OBJECT-TYPE
       SYNTAX CerentGenericAlarmEntry
       MAX-ACCESS not-accessible
       STATUS current
       DESCRIPTION
              "Row definition for cerentGenericAlarmTable"
       INDEX { cerentGenericAlarmIndex, cerentGenericAlarmType }
       ::= { cerentGenericAlarmTable 1 }

CerentGenericAlarmEntry ::= SEQUENCE {
       cerentGenericAlarmIndex           	Integer32,
       cerentGenericAlarmObjectType      	CerentGenericEntityClass,
       cerentGenericAlarmSlotNumber      	Integer32,
       cerentGenericAlarmPortNumber      	CerentPortNumber,
       cerentGenericAlarmLineNumber      	Integer32,
       cerentGenericAlarmObjectIndex     	Integer32,
       cerentGenericAlarmType            	CerentGenericAlarmType, 
       cerentGenericAlarmState           	CerentNotificationClass,
       cerentGenericAlarmTimeStamp       	TimeStamp,
       cerentGenericAlarmObjectName      	DisplayString,
       cerentGenericAlarmAdditionalInfo  	DisplayString,
       cerentGenericAlarmSeverity	 	CerentAlarmSeverity,
       cerentGenericAlarmStatus		 	CerentAlarmStatus,
       cerentGenericAlarmServiceAffecting	CerentAlarmServiceAffecting
       }

cerentGenericAlarmIndex       OBJECT-TYPE
       SYNTAX Integer32 ( 1..2147483647 ) -- all +ve values
       MAX-ACCESS not-accessible
       STATUS current
       DESCRIPTION
              "Uniquely identifies each entry in alarm table.
               May not start with one and there may be some
               missing numbers."
       ::= { cerentGenericAlarmEntry 10 }

cerentGenericAlarmObjectType       OBJECT-TYPE
       SYNTAX CerentGenericEntityClass
       MAX-ACCESS read-only
       STATUS current
       DESCRIPTION
              "This will indicate what is the type
               of the entity which raised this alarm.
               ( E.g., DS3, etherBridge, VT-TERM, etc ) 
               The NMS is expected to use this value
               to decide which table to poll for 
               further info about the alarm"
       ::= { cerentGenericAlarmEntry 20 }

cerentGenericAlarmSlotNumber           OBJECT-TYPE
       SYNTAX Integer32
       MAX-ACCESS read-only
       STATUS current
       DESCRIPTION
              "This will indicate what is the slot 
               of the object which raised this alarm.
               If not relevant to the alarm, will be
               zero."
       ::= { cerentGenericAlarmEntry 30 }

cerentGenericAlarmPortNumber          OBJECT-TYPE
       SYNTAX CerentPortNumber 
       MAX-ACCESS read-only
       STATUS current
       DESCRIPTION
              "This will indicate what is the port
               of the object which raised this alarm."
       ::= { cerentGenericAlarmEntry 40 }
 
cerentGenericAlarmLineNumber           OBJECT-TYPE
       SYNTAX Integer32
       MAX-ACCESS read-only
       STATUS     current
       DESCRIPTION
              "This will indicate what is the port
               of the object which raised this alarm.
               If not relevant to the alarm, will be
               zero."
       ::= { cerentGenericAlarmEntry 50 }

cerentGenericAlarmObjectIndex       OBJECT-TYPE
       SYNTAX Integer32
       MAX-ACCESS read-only
       STATUS current
       DESCRIPTION
              "Every alarm is raised by an object and 
               this object is an entry in a specific 
               table. This is the index of the object
               in that table E.g., if the alarm is interface
               related, this index is the index of the
               interface in the interface table."
       ::= { cerentGenericAlarmEntry 60 }

cerentGenericAlarmType       OBJECT-TYPE
       SYNTAX CerentGenericAlarmType
       MAX-ACCESS read-only
       STATUS current
       DESCRIPTION
              "Indicates what the exact nature of the
               alarm. See the CerentGenericAlarmType TC
               for mapping details "
       ::= {cerentGenericAlarmEntry  70 }

cerentGenericAlarmState OBJECT-TYPE  
       SYNTAX        CerentNotificationClass
       MAX-ACCESS read-only
       STATUS current
       DESCRIPTION
              "Specifies alarm severity and service 
               affecting status ( SA/NSA ). Only 
               {minor|major|critical}+{NA|NSA} alarms and
               standing conditions will be represented here.

               However, this mib object is included in each
               trap dispatched and in the trap this object
               can contain all the possible values of
               CerentNotificationClass type."
       ::= { cerentGenericAlarmEntry 80 }

cerentGenericAlarmTimeStamp OBJECT-TYPE  
       SYNTAX   TimeStamp
       MAX-ACCESS read-only
       STATUS current
       DESCRIPTION
              "The value of sysUpTime when this entry was
               created. This is accurate only upto a second."
       ::= { cerentGenericAlarmEntry 90 }

cerentGenericAlarmObjectName OBJECT-TYPE
       SYNTAX  DisplayString
       MAX-ACCESS read-only
       STATUS current
       DESCRIPTION
              "TL1-style user-visible name which uniquely
               identifies an object in the system"
       ::= { cerentGenericAlarmEntry 100 }

cerentGenericAlarmAdditionalInfo OBJECT-TYPE
       SYNTAX  DisplayString 
       MAX-ACCESS read-only
       STATUS current
       DESCRIPTION
              "Additional information for the alarm object.
              In the current version of the MIB, this object 
              contains the following information :-
              
              a) Provisioned description for alarms of type
              'failureDetectedExternalToTheNE'.

              This object would be a null string if no 
              additional information is specified."
       ::= { cerentGenericAlarmEntry 110 }
       
cerentGenericAlarmSeverity OBJECT-TYPE
       SYNTAX       CerentAlarmSeverity
       MAX-ACCESS read-only
       STATUS current
       DESCRIPTION
              "Specifies severity of the alarm
               being sent out." 

       ::= { cerentGenericAlarmEntry 120 }

cerentGenericAlarmStatus OBJECT-TYPE
       SYNTAX       CerentAlarmStatus
       MAX-ACCESS read-only
       STATUS current
       DESCRIPTION
              "Represents if an alarm is currently raised or cleared."

       ::= { cerentGenericAlarmEntry 130 }

cerentGenericAlarmServiceAffecting OBJECT-TYPE
       SYNTAX       CerentAlarmServiceAffecting
       MAX-ACCESS read-only
       STATUS current
       DESCRIPTION
              "Specifies whether the alarm that is being
               sent out is Service Affecting (SA) or Non-
               Service Affecting (NSA)."

       ::= { cerentGenericAlarmEntry 140 }


cerentGenericReportedAlarmCount       OBJECT-TYPE
       SYNTAX       Unsigned32
       MAX-ACCESS   read-only
       STATUS current
       DESCRIPTION
           "Number of alarms currently reported against Cisco
            ONS platform. This equals the number of rows in
            cerentGenericReportedAlarmTable."
       ::= { cerentGenericAlarmGroup 30 }


cerentGenericReportedAlarmTable       OBJECT-TYPE
       SYNTAX SEQUENCE OF CerentGenericReportedAlarmEntry
       MAX-ACCESS not-accessible
       STATUS current
       DESCRIPTION
              "This table has the list of alarms currently
               reported for the Cisco ONS node. It does not
               include any cleared alarms. The alarms in this
               table are in compliance with Telcordia GR-253.
               This means that if a network problem causes two
               alarms, such a as loss of frame(LOF) and loss of
               signal(LOS), only LOS alarm will be in this table
                because it supersedes and replaces the LOF."
       ::= { cerentGenericAlarmGroup 40 }

cerentGenericReportedAlarmEntry       OBJECT-TYPE
       SYNTAX CerentGenericReportedAlarmEntry
       MAX-ACCESS not-accessible
       STATUS current
       DESCRIPTION
              "Row definition for cerentGenericReportedAlarmTable"
       INDEX { cerentGenericReportedAlarmIndex, cerentGenericReportedAlarmType }
       ::= { cerentGenericReportedAlarmTable 1 }

CerentGenericReportedAlarmEntry ::= SEQUENCE {
       cerentGenericReportedAlarmIndex               Integer32,
       cerentGenericReportedAlarmObjectType          CerentGenericEntityClass,
       cerentGenericReportedAlarmSlotNumber          Integer32,
       cerentGenericReportedAlarmPortNumber          CerentPortNumber,
       cerentGenericReportedAlarmObjectIndex         Integer32,
       cerentGenericReportedAlarmType                CerentGenericAlarmType,
       cerentGenericReportedAlarmTimeStamp           TimeStamp,
       cerentGenericReportedAlarmObjectName          DisplayString,
       cerentGenericReportedAlarmAdditionalInfo      DisplayString,
       cerentGenericReportedAlarmSeverity            CerentAlarmSeverity,
       cerentGenericReportedAlarmStatus              CerentAlarmStatus,
       cerentGenericReportedAlarmServiceAffecting    CerentAlarmServiceAffecting
       }

cerentGenericReportedAlarmIndex       OBJECT-TYPE
       SYNTAX Integer32 ( 1..2147483647 ) -- all +ve values
       MAX-ACCESS not-accessible
       STATUS current
       DESCRIPTION
              "Identifies each entry in ReportedAlarm table.
               May not start with one and there may be some
               missing numbers."
       ::= { cerentGenericReportedAlarmEntry 10 }

cerentGenericReportedAlarmObjectType       OBJECT-TYPE
       SYNTAX CerentGenericEntityClass
       MAX-ACCESS read-only
       STATUS current
       DESCRIPTION
              "This will indicate the type
               of the entity which raised this alarm.
               ( E.g., DS3, etherBridge, VT-TERM, etc )
               The NMS is expected to use this value
               to decide which table to poll for
               further info about the alarm"
       ::= { cerentGenericReportedAlarmEntry 20 }

cerentGenericReportedAlarmSlotNumber           OBJECT-TYPE
       SYNTAX Integer32
       MAX-ACCESS read-only
       STATUS current
       DESCRIPTION
              "This will indicate what is the slot
               of the object which raised this alarm.
               If not relevant to the alarm, will be
               zero."
       ::= { cerentGenericReportedAlarmEntry 30 }

cerentGenericReportedAlarmPortNumber          OBJECT-TYPE
       SYNTAX CerentPortNumber
       MAX-ACCESS read-only
       STATUS current
       DESCRIPTION
              "This will indicate what is the port
               of the object which raised this alarm."
       ::= { cerentGenericReportedAlarmEntry 40 }

cerentGenericReportedAlarmObjectIndex       OBJECT-TYPE
       SYNTAX Integer32
       MAX-ACCESS read-only
       STATUS current
       DESCRIPTION
              "Every alarm is raised by an object and
               this object is an entry in a specific
               table. This is the index of the object
               in that table E.g., if the alarm is interface
               related, this is the index of the
               interface in the interface table."
       ::= { cerentGenericReportedAlarmEntry 50 }

cerentGenericReportedAlarmType       OBJECT-TYPE
       SYNTAX CerentGenericAlarmType
       MAX-ACCESS read-only
       STATUS current
       DESCRIPTION
              "Indicates the exact nature of the
               alarm." 
       ::= {cerentGenericReportedAlarmEntry  60 }

cerentGenericReportedAlarmTimeStamp OBJECT-TYPE
       SYNTAX   TimeStamp
       MAX-ACCESS read-only
       STATUS current
       DESCRIPTION
              "The value of sysUpTime when this entry was
               created. This is accurate only upto a second."
       ::= { cerentGenericReportedAlarmEntry 70 }

cerentGenericReportedAlarmObjectName OBJECT-TYPE
       SYNTAX  DisplayString
       MAX-ACCESS read-only
       STATUS current
       DESCRIPTION
              "TL1-style user-visible name which uniquely
               identifies an object in the system"
       ::= { cerentGenericReportedAlarmEntry 80 }

cerentGenericReportedAlarmAdditionalInfo OBJECT-TYPE
       SYNTAX  DisplayString
       MAX-ACCESS read-only
       STATUS current
       DESCRIPTION
              "Additional information for the alarm object.
              In the current version of the MIB, this object
              contains the following information :-

              a) Provisioned description for alarms of type
              'failureDetectedExternalToTheNE'.

              This object would be a null string if no
              additional information is specified."
       ::= { cerentGenericReportedAlarmEntry 90 }

cerentGenericReportedAlarmSeverity OBJECT-TYPE
       SYNTAX       CerentAlarmSeverity
       MAX-ACCESS read-only
       STATUS current
       DESCRIPTION
              "Specifies severity of the alarm."

       ::= { cerentGenericReportedAlarmEntry 100 }

cerentGenericReportedAlarmStatus OBJECT-TYPE
       SYNTAX       CerentAlarmStatus
       MAX-ACCESS read-only
       STATUS current
       DESCRIPTION
              "Represents if the alarm is currently raised
               or cleared."

       ::= { cerentGenericReportedAlarmEntry 110 }

cerentGenericReportedAlarmServiceAffecting OBJECT-TYPE
       SYNTAX       CerentAlarmServiceAffecting
       MAX-ACCESS read-only
       STATUS current
       DESCRIPTION
              "Specifies whether the alarm that is being
               sent out is Service Affecting (SA) or Non-
               Service Affecting (NSA)."

       ::= { cerentGenericReportedAlarmEntry 120 }


--  All Cisco ONS Generic Threshold Group.

cerentGenericThresholdGroup OBJECT-IDENTITY
       STATUS       current
       DESCRIPTION
              "The group that will represent all the
               threshold info in the Cisco ONS network element,
               ONS 15327, 15310"
       ::= { cerentGenericObjects 40 }

cerentGenericThresholdTable       OBJECT-TYPE
       SYNTAX SEQUENCE OF CerentGenericThresholdEntry
       MAX-ACCESS not-accessible
       STATUS current
       DESCRIPTION
              "This table holds all the provisioned 
               Thresholds.  
   
               This table is currently unimplemented."
       ::= { cerentGenericThresholdGroup 10 }

cerentGenericThresholdEntry       OBJECT-TYPE
       SYNTAX CerentGenericThresholdEntry
       MAX-ACCESS not-accessible
       STATUS current
       DESCRIPTION
              "Row definition for cerentGenericThresholdTable"
       INDEX { cerentGenericThresholdIndex }
       ::= { cerentGenericThresholdTable 1 }

CerentGenericThresholdEntry ::= SEQUENCE {
      cerentGenericThresholdIndex           Integer32,
      cerentGenericThresholdMonitorType     CerentMonitorType,
      cerentGenericThresholdLocation        CerentLocation,
      cerentGenericThresholdPeriod          CerentPeriod,
      cerentGenericThresholdSetValue        Integer32,
      cerentGenericThresholdCurrentValue    Integer32,
      cerentGenericThresholdDetectType      INTEGER
    }

cerentGenericThresholdIndex  OBJECT-TYPE
       SYNTAX  Integer32 (1..2147483647) -- Same as IfIndex from IF-MIB
       MAX-ACCESS not-accessible
       STATUS current
       DESCRIPTION
              "Uniquely identifies each entry in Threshold table.
               May not start with one and there will be some
               missing numbers."
       ::= { cerentGenericThresholdEntry 10 }

cerentGenericThresholdMonitorType  OBJECT-TYPE
       SYNTAX                  CerentMonitorType
       MAX-ACCESS read-only
       STATUS current
       DESCRIPTION
       "This object indicates the type of metric monitored."
       ::= { cerentGenericThresholdEntry 20 }

cerentGenericThresholdLocation     OBJECT-TYPE
       SYNTAX                  CerentLocation
       MAX-ACCESS read-only
       STATUS current
       DESCRIPTION
       "This indicates if it near or far end"
       ::= { cerentGenericThresholdEntry 30 }

cerentGenericThresholdPeriod       OBJECT-TYPE
       SYNTAX                  CerentPeriod
       MAX-ACCESS read-only
       STATUS current
       DESCRIPTION
       "The sampling interval period is indicated here"
       ::= { cerentGenericThresholdEntry 40 }

cerentGenericThresholdSetValue     OBJECT-TYPE
       SYNTAX                  Integer32
       MAX-ACCESS read-only
       STATUS current
       DESCRIPTION
       "The value of this object will be threshold that was 
        provisioned by the NMS"
       ::= { cerentGenericThresholdEntry 50 }

cerentGenericThresholdCurrentValue OBJECT-TYPE
       SYNTAX                  Integer32
       MAX-ACCESS read-only
       STATUS current
       DESCRIPTION
       "The current value of the counter which 
        measures the metric.

        This column will never be implemented as
        these values are already accessible through
        IETF MIB objects."

       ::= { cerentGenericThresholdEntry 60 }

cerentGenericThresholdDetectType  OBJECT-TYPE
       SYNTAX  INTEGER {
                  unknown(1),
                  none(10),
                  mon(20),
                  term(30) 
                  }
       MAX-ACCESS read-only
       STATUS current
       DESCRIPTION
       "The value of this object will be the detect type for the
        threshold."
       ::= { cerentGenericThresholdEntry 70 }      

--  All Cisco ONS Generic Notifications definitions.

cerentGenericEvents OBJECT-IDENTITY
      STATUS      current
      DESCRIPTION
            "Place holder for all notifications
             of Cisco ONS network device, ONS 15327, 15310 "
      ::= { cerentGeneric 20 }

cerentGenericV2Events OBJECT-IDENTITY
      STATUS      current
      DESCRIPTION
                 "The sub-identifier has to be zero, as part
                  of the interoperability agreement between
                  SNMPv1 and SNMPv2 worlds."
      ::= { cerentGenericEvents 0  } 

-- ---------------------------------------------
-- All the Cisco ONS generic notifications definitions
-- ---------------------------------------------

-- object and event groups

alarmUnknown
  NOTIFICATION-TYPE 
    OBJECTS { 
        cerentGenericNodeTime, 
        cerentGenericAlarmState,
        cerentGenericAlarmObjectType, 
        cerentGenericAlarmObjectIndex,
        cerentGenericAlarmSlotNumber, 
        cerentGenericAlarmPortNumber, 
        cerentGenericAlarmLineNumber,
        cerentGenericAlarmObjectName,
        cerentGenericAlarmSeverity,
        cerentGenericAlarmStatus,
        cerentGenericAlarmServiceAffecting
    }
    STATUS current 
    DESCRIPTION "alarm unknown" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events  1 } 

alarmCutoffIsInManualMode
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "alarm cutoff is in manual mode" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 10 }
 
failureDetectedExternalToTheNE
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmAdditionalInfo,
      cerentGenericAlarmSeverity,
      cerentGenericAlarmStatus,
      cerentGenericAlarmServiceAffecting
    }
    STATUS current 
    DESCRIPTION "failure detected External to the NE" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 20 }

externalError
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "external error" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 30 }
 
excessiveSwitching
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "excessive switching" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 40 }
 
sdccTerminationFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "SDCC Termination failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 50 }
 
incomingFailureCondition
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "incoming failure condition" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 60 }
 
alarmIndicationSignal       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "alarm indication signal" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 70 }
 
alarmIndicationSignalLine
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "alarm indication signal LINE" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 80 }
 
alarmIndicationSignalPath  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "alarm indication signal Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 90 }
 
alarmIndicationSignalVT    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "alarm indication signal VT" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 100 }

apsChannelFailure           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "channel failure APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 110 }
 
channelByteFailureAPS      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "channel Byte failure APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 120 }
 
channelProtectionSwitchingChannelMatchFailureAPS   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "channel Protection Switching Channel Match failure APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 130 }
 
channelAutomaticProtectionSwitchModeMismatchAPS    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "channel Automatic Protection Switch Mode Mismatch APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 140 }
 
farEndProtectionLineFailure              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "channel far end protection line failure APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 150 }
 
inconsistentAPSCode       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Inconsistent APS code" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 160 }
 
improperAPSCode       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Improper APS code APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 170 }
 
nodeIdMismatch        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Node Id Mismatch APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 180 }
 
channelDefaultKAPS    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Default K APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 190 }
 
connectionLoss         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Connection loss APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 200 }
 
bipolarViolation             
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "bipolar Violation" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 210 }
 
carrierLossOnTheLAN       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "carrier Loss on the LAN" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 220 }
 
concatenationErrorSTS
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "concatenation error STS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 230 }
 
excessCollisionsOnTheLAN  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "excess collisions on the LAN" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 240 }
 
facilityFailure   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility critical alarm caused by DS3 facility failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 250 }
 
farEndAIS   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end AIS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 260 }
 
farEndMultipleDS1LOSDetectedOnDS3 
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end Multiple DS1 LOS detected on DS3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 270 }
 
farEndDS1EqptFailNonServiceAffecting              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end DS1 eqpt fail non service affecting" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 280 }
 
farEndDS1EqptFailServiceAffecting  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end DS1 Eqpt fail service affecting" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 290 }
 
farEndSingleDS1LOS        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end Single DS1 LOS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 300 }
 
farEndDS3EqptFailNonServiceAffecting              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end DS3 Eqpt failure non service affecting" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 310 }
 
farEndDS3EqptFailServiceAffecting  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end DS3 Eqpt failure service affecting" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 320 }
 
farEndCommonEquipmentFailureNonServiceAffecting              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end common Eqpt failure non service affecting" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 330 }
 
farEndIDLE  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end IDLE" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 340 }
 
farEndLOS   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end LOS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 350 }
 
farEndLOF   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end LOF" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 360 }
 
farEndBlockError           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far End Block Error" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 370 }
 
ds3IdleCondition            
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "idle Condition DS3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 380 }
 
lossOfFrame 
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loss of Frame" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 390 }
 
lossOfPointer               
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loss of Pointer" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 400 }
 
lossOfPointerPath
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loss of Pointer Path " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 410 }
 
lossOfPointerVT            
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loss of Pointer VT" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 420 }
 
lossOfSignal                
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loss of Signal" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 430 }
 
outOfFrame  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "out of Frame" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 440 }
 
pathSelectorFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "path Selector inability to swtich to a valid signal" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 450 }
 
remoteAlarmIndication       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Alarm Indication" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 460 }
 
remoteFailureIndication     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Failure Indication" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 470 }
 
remoteFailureIndicationLine           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Failure Indication LINE" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 480 }
 
remoteFailureIndicationPath           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Failure Indication Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 490 }
 
remoteFailureIndicationVT  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Failure Indication VT" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 500 }
 
signalDegrade
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Signal Degrade" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 510 }
 
severelyErroredFrame        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "severely Errored Frame" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 520 }
 
signalFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Signal Failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 530 }
 
signalLabelMismatchFailure     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "signal Label Mismatch Failures" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 540 }
 
payloadDefectIndication  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Payload Defect Indication" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 550 }

payloadDefectIndicationPath 
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Payload Defect Indication - Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 560 }
 
payloadLabelMismatchPath      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Payload Label Mismatch - Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 570 }
 
signalLabelMismatchFailurePayloadLabelMismatchVT        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "signal Label Mismatch Failure Payload Label Mismatch VT" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 580 }
 
unequippedPath  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Unequipped - Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 590 }
 
signalLabelMismatchFailureUnequippedVT    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "signal Label Mismatch Failure Unequipped VT" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 600 }
 
lossOfSynchronization         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Loss of Synchronization"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 610 }
 
outOfSynchronization
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Out of Synchronization"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 620 }
 
primarySynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Primary Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 630 }
 
secondarySynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Secondary Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 640 }
 
thirdSynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Third Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 650 }
 
fourthSynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Fourth Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 660 }
 
fifthSynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Fifth Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 670 }
 
sixthSynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Sixth Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 680 }
 
failedToReceiveSynchronizationStatusMessage 
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failed to receive Synchronization Status Message" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 690 }

synchronizationStatusMessagesAreDisabledOnThisInterface
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "synchronization Status Messages are disabled on this interface" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 700 }

stratum1PrimaryReferenceSourceTraceable     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Stratum1 Primary Reference Source Traceable" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 710 }

synchronizedTraceabilityUnknown     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "synchronized Traceability Unknown" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 720 }

stratum2Traceable   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "stratum 2 Traceable " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 730 }

transitNodeClockTraceable          
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "transit Node clock Traceable" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 740 }

stratum3ETraceable  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "stratum 3E Traceable" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 750 }

stratum3Traceable   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "stratum 3 Traceable" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 760 }

sonetMinimumClockTraceable
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Minimum clock Traceable - SONET " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 770 }

stratum4Traceable   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "stratum 4 Traceable" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 780 }

doNotUseForSynchronization        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "do not Use for Synchronization" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 790 }

reservedForNetworkSynchronizationUse         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "reserved for Network Synchronization Use" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 800 }

outgoingFailureCondition            
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "outgoing failure condition" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 810 }
 
remoteDefectIndicationLine         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Defect Indication LINE" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 820 }
 
remoteDefectIndicationPath         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Defect Indication Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 830 }
 
freeRunningSynchronizationMode     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "free Running Synchronization mode" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 840 }
 
holdoverSynchronizationMode         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "holdover synchronization mode" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 850 }
 
fastStartSynchronizationMode       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "fast Start synchronization mode" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 860 }
 
internalFault
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "internal hardware fault or failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 870 }
 
internalError
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "error Internal to the NE Detected" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 880 }
 
internalMessageError                
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "internal Message Error" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 890 }
 
mismatchOfEquipmentAndAttributes  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "mismatch of Equipment and Attributes" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 900 }
 
watchdogTimerTimeout                
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "watchdog Timer Timeout" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 910 }
 
softwareFaultOrFailure             
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "software Fault or failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 920 }
 
softwareFaultDataIntegrityFault   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "software Fault -  Data integrity fault :
                 The newly added provisioning or hardware has 
                 caused the database to grow beyond its limit. 
                 That is, the newly added object(s) in the system 
                 has(have) enough memory to exist onboard but
                 too large to be saved in the database." 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 930 }
 
programFailure       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "program failure " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 940 }
 
controlEquipmentFailure            
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 950 }
 
primaryNonVolatileBackupMemoryFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Primary non volatile Backup Memory failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 960 }
 
secondaryNonVolatileBackupMemoryFailure 
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Secondary non volatile Backup Memory failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 970 }
 
controlBusFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Control Bus failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 980 }
 
controlBus1Failure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Control Bus 1 failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 990 }
 
controlBus2Failure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Control Bus 2 failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1000 }

tccAToShelfSlot1DROP1CommunicationFailure NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 1" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1010 }

tccAToShelfSlot2DROP2CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 2" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1020 }

tccAToShelfSlot3DROP3CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1030 }

tccAToShelfSlot4DROP4CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 4" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1040 }

tccAToShelfSlot5TRUNK1CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 5" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1050 }

tccAToShelfSlot6TRUNK2CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 6" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1060 }

tccAToShelfSlot7TCCACommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 7 " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1070 }

tccAToShelfSlot8XCONACommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 8" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1080 }

tccAToShelfSlot9AICCommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 9" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1090 }

tccAToShelfSlot10XCONBCommunicationFailure NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 10" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1100 }

tccAToShelfSlot11TCCBCommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 11" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1110 }

tccAToShelfSlot12TRUNK3CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 12" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1120 }

tccAToShelfSlot13TRUNK4CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 13" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1130 }

tccAToShelfSlot14DROP5CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 14" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1140 }

tccAToShelfSlot15DROP6CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 15" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1150 }

tccAToShelfSlot16DROP7CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 16" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1160 }

tccAToShelfSlot17DROP8CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 17 " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1170 }

tccAToDCCAProcessorCommunicationFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure ControllerP A to ControllerJ A processor" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1180 }

tccBToShelfSlot1DROP1CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 1 " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1190 }

tccBToShelfSlot2DROP2CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 2" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1200 }

tccBToShelfSlot3DROP3CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1210 }

tccBToShelfSlot4DROP4CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 4" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1220 }

tccBToShelfSlot5TRUNK1CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 5" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1230 }

tccBToShelfSlot6TRUNK2CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 6" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1240 }

tccBToShelfSlot7TCCACommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 7" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1250 }

tccBToShelfSlot8XCONACommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 8" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1260 }

tccBToShelfSlot9AICCommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 9" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1270 }

tccBToShelfSlot10XCONBCommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 10" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1280 }

tccBToShelfSlot11TCCBCommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 11" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1290 }

tccBToShelfSlot12TRUNK3CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 12" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1300 }

tccBToShelfSlot13TRUNK4CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 13" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1310 }

tccBToShelfSlot14DROP5CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 14" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1320 }

tccBToShelfSlot15DROP6CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 15" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1330 }

tccBToShelfSlot16DROP7CommunicationFailure 
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 16" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1340 }

tccBToShelfSlot17DROP8CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 17" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1350 }

tccBToDCCBProcessorCommunicationFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure ControllerP B to ControllerJ A processor" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1360 }

controlEquipmentControlCommunicationsEquipmentFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS deprecated 
    DESCRIPTION "control Equipment Control Communications equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1370 }

controlProcessorFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Control processor failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1380 }

workingMemoryFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Working memory failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1390 }

interconnectionEquipmentFailure         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1400 }

payloadBusFailureToIOSlot1XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 1 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1410 }

payloadBusFailureToIOSlot2XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 2 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1420 }

payloadBusFailureToIOSlot3XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 3 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1430 }

payloadBusFailureToIOSlot4XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 4 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1440 }

payloadBusFailureToIOSlot5XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 5 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1450 }

payloadBusFailureToIOSlot6XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 6 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1460 }

payloadBusFailureToIOSlot12XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 7 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1470 }

payloadBusFailureToIOSlot13XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 8 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1480 }

payloadBusFailureToIOSlot14XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 9 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1490 }

payloadBusFailureToIOSlot15XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 10 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1500 }

payloadBusFailureToIOSlot16XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 11 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1510 }

payloadBusFailureToIOSlot17XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 12 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1520 }

payloadBusFailureToIOSlot1XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 1 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1530 }

payloadBusFailureToIOSlot2XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 2 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1540 }

payloadBusFailureToIOSlot3XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 3 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1550 }

payloadBusFailureToIOSlot4XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 4 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1560 }

payloadBusFailureToIOSlot5XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 5 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1570 }

payloadBusFailureToIOSlot6XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 6 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1580 }

payloadBusFailureToIOSlot12XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 7 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1590 }

payloadBusFailureToIOSlot13XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 8 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1600 }

payloadBusFailureToIOSlot14XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 9 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1610 }

payloadBusFailureToIOSlot15XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 10 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1620 }

payloadBusFailureToIOSlot16XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 11 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1630 }

payloadBusFailureToIOSlot17XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 12 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1640 }

timeSlotInterchangeEquipmentFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Eqpt Time slot interchange eqpt failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1650 }

equipmentFailure           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1660 }

highTemperature        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "High Temperature" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1670 }

invalidMACAddress
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment failure Invalid MAC Address" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1680 }

boardFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment failure Board Failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1690 }

diagnosticFailure     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment failure Diagnostics Failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1700 }

mediumAccessControlFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment failure Medium Access Control" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1710 }

facilityTerminationEquipmentFailure    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility Termination equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1720 }

automaticLaserShutoffDueToHighTemperature              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Automatic Laser Shutoff Due To High Temperature" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1730 }

failureToReleaseFromProtection        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure To Release from protection" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1740 }

receiverFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility Termination equipment Receiver failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1750 }

transmitFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility Termination equipment Transmit failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1760 }

facilityTerminationEquipmentReceiverMissing      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility Termination equipment Receiver missing" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1770 }

facilityTerminationEquipmentTransmitterMissing   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility Termination equipment Transmitter missing" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1780 }

failureToSwitchToProtection           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure To Switch to protection" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1790 }

failureToSwitchToProtectionRing      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure To Switch to protection Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1800 }

failureToSwitchToProtectionSpan      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure To Switch to protection Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1810 }

failureToSwitchToProtectionPath      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure to Switch to protection Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1820 }

fanFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure of cooling fan tray" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1830 }

equipmentUnitPlugIn    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment unit plug in" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1840 }

nePowerFailureAtConnector
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "NE Power Failure At Connector" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1850 }

fuseAlarm
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "power failure Fuse Alarm" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1860 }

synchronizationUnitFailure              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "synchronization unit failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1870 }

synchronizationSwitchingEquipmentFailure          
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "synchronization switching Equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1880 }

equipmentUnitUnplugged
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment unit un plug" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1890 }

loopback                 
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loop back" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1900 }

ds1LoopbackDueToFEACCommand
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback due to FEAC command DS1" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1910 }

loopbackCommandSentToFarEndDS1
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback Command sent to Far End DS1" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1920 }

ds3LoopbackDueToFEACCommand          
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback due to FEAC command DS3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1930 }

ds3LoopbackCommandSentToFarEnd
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback Command sent to Far End DS3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1940 }

ds2LoopbackDueToFarEndCommand
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback due to Far End Command DS2" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1950 }

ds2LoopbackCommandSentToFarEnd
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback Command sent to Far End DS2" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1960 }

facilityLoopback
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loop back facility" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1970 }

networkLoopback 
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loop back Network" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1980 }

terminalLoopback
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loop back Terminal" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1990 }

manuallyCausedAbnormalCondition        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manually caused abnormal condition" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2000 }

ethernetBridgeIsNewRootOfSpanningTree  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "new Root discovered in bridged network" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2010 }

ethernetBridgeTopologyChange        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "topology change discovered in bridged network" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2020 }

normalCondition          
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "normal condition" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2030 }

embeddedOperationsChannelFailureLinkDown        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "embedded Operations Channel failure link down" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2040 }

peerStateMismatch       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "peer state mismatch" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2050 }

proceduralError          
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "procedural Error" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2060 }

improperRemoval         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Improper Removal" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2070 }

duplicateNodeID
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Duplicate Node ID" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2080 }

blsrOutOfSync         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "BLSR out of sync" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2090 }

blsrMultiNodeTableUpdateCompleted
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "BLSR tables resynchronized" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2100 }

protectionUnitNotAvailable             
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "protection unit not available" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2110 }

performanceMonitorThresholdCrossingAlert         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericThresholdMonitorType,
      cerentGenericThresholdLocation,
      cerentGenericThresholdPeriod,
      cerentGenericThresholdSetValue,
      cerentGenericThresholdCurrentValue,
      cerentGenericThresholdDetectType,
      cerentGenericAlarmSeverity,
      cerentGenericAlarmStatus,
      cerentGenericAlarmServiceAffecting
    }
    STATUS current 
    DESCRIPTION "performance Monitor Threshold Crossing Alert" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2120 }

protectionSwitch
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "occurrence of a protection switching event" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2130 }

recoveryOrServiceProtectionActionHasBeenInitiated             
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "recovery or service protection action has been initiated" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2140 }

automaticSystemReset    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic system Reset" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2150 }

automaticUPSRSwitchCausedByAIS      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by AIS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2160 }

automaticUPSRSwitchCausedByLOP      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by Lop" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2170 }

automaticUPSRSwitchCausedByUNEQ
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by Uneq" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2180 }

automaticUPSRSwitchCausedByPDI      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by PDI" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2190 }

automaticUPSRSwitchCausedBySFBER
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by Sfber" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2200 }

automaticUPSRSwitchCausedBySDBER
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by Sdber"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2210 }

coldRestart              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "cold Restart" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2220 }

forcedSwitchBackToWorking
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched to working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2230 }

forcedSwitchBackToWorkingRing
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched to working Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2240 }

forcedSwitchBackToWorkingSpan
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched to working Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2250 }

forcedSwitchToProtection
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched protection unit" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2260 }

forcedSwitchToProtectionRing
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched protection unit Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2270 }

forcedSwitchToProtectionSpan
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched protection unit Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2280 }

workingFacilityOrEquipmentForcedToSwitchToProtectionPath
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched protection unit Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2290 }

initializationInitiated      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "initialization initiated" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2300 }

lockoutOfProtection         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of Protection" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2310 }

lockoutOfProtectionRing    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of Protection Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2320 }

lockoutOfProtectionSpan    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of Protection Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2330 }

lockoutOfProtectionPath    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of Protection Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2340 }

lockoutOfWorking            
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2350 }

lockoutOfWorkingRing       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of working Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2360 }

lockoutOfWorkingSpan       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of working Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2370 }

manualSystemReset           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual system Reset" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2380 }

manualSwitchToInternalClock
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual switch to internal clock" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2390 }

manualSwitchToPrimaryReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Primary refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2400 }

manualSwitchToSecondReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Second reference" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2410 }

manualSwitchToThirdReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Third refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2420 }

manualSwitchToFourthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Fourth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2430 }

manualSwitchToFifthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Fifth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2440 }

manualSwitchToSixthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Sixth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2450 }

manualSwitchBackToWorking
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manualSwitch of working facility or eqpt to protection Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2460 }

manualSwitchBackToWorkingRing
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manualSwitch of working facility or eqpt to protection Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2470 }

manualSwitchBackToWorkingSpan
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manualSwitch of working facility or eqpt to protection" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2480 }

manualSwitchToProtection
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manualSwitch of Working facility or eqpt to Protection unit" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2490 }

manualSwitchToProtectionRing
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt manualSwitch to Protection unit Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2500 }

manualSwitchToProtectionSpan
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt manualSwitch to Protection unit Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2510 }

manualSwitchOfWorkingFacilityOrEquipmentToProtectionPath
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manualSwitch of working facility or eqpt to Protection Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2520 }

powerfailRestart
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Powerfail Restart" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2530 }

ringIsSquelchingTraffic     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "ring is squelching traffic" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2540 }

softwareDownloadInProgress  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "software download in progress"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2550 }

switchToInternalClock
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Internal clock" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2560 }

switchToPrimaryReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Primary refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2570 }

switchToSecondReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Second refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2580 }

switchToThirdReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Third refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2590 }

switchToFourthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Fourth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2600 }

switchToFifthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Fifth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2610 }

switchToSixthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Sixth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2620 }

systemReboot    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "system reboot" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2630 }

switchedBackToWorking      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switched Back To Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2640 }

switchedToProtection
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switched To Protection" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2650 }

warmRestart     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "warm Restart" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2660 }

ringIsInWaitToRestoreState
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Ring is in Wait To Restore state" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2670 }

manualSwitchRequest              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Manual Switch Request" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2680 }

forcedSwitchRequest               
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Forced Switch Request" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2690 }

lockoutSwitchRequest
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Lockout Switch Request" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2700 } 

rmonHistoriesAndAlarmsResetReboot
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RMON histories and alarms have been reset due to chipset reboot"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2710 }

rmonThresholdCrossingAlarm
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
   }
   STATUS current
    DESCRIPTION "Crossing of Falling/Rising Threshold detected"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2720 }

alarmsSuppressedByUserCommand
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Alarms Suppressed By User Command"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2730 }

alarmsSuppressedForMaintenance
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Alarms Suppressed For Maintenance"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2740 }

switchingMatrixModuleFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Switching Matrix Module Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2750 }

lanConnectionPolarityReversed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Lan Connection Polarity Reversed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2760 }

autonomousPMReportMessageInhibited
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Autonomous Performance Monitoring Report Message Inhibited"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2780 }

ioSlotToXCONCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "IO Slot To XCON Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2790 }

stsPathTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "STS path trace identifier mismatch"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2800 }

nePowerFailureAtConnectorA 
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "NE power failure at connector A"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2810 }

nePowerFailureAtConnectorB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "NE power failure at connector B"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2820 }

freeMemoryOnCardVeryLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Free memory on the card is very low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2830 }

freeMemoryOnCardNearZero  
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Free memory on the card is near zero"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2840 }

exerciseRequestOnRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercise Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2850 }

exerciseRequestOnSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercise Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2860 }

squelchingPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Squelching Path: "

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2870 }

extraTrafficPreempted
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extra Traffic Preempted."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2880 }

farEndLockoutOfWorkingRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Lockout of working - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2890 }

farEndLockoutOfWorkingSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Lockout of working - Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2900 }

farEndLockoutOfProtectionRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Lockout of Protection - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2910 }

farEndLockoutOfProtectionAllSpans
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Lockout of Protection - All Spans."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2920 }

farEndWorkingFacilityForcedToSwitchToProtectionRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Working facility forced to switch to protection unit - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2930 }

farEndWorkingFacilityForcedToSwitchToProtectionSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Working facility forced to switch to protection unit - Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2940 }

farEndManualSwitchOfWorkingFacilityToProtectionRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Manual Switch of Working facility to Protection unit - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2950 }

farEndManualSwitchOfWorkingFacilityToProtectionSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Manual Switch of Working facility to Protection unit - Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2960 }

farEndExercisingRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Exercise Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2970 }

farEndExercisingSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Exercise Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2980 }

farEndBERThresholdPassedForSignalFailureRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End BER threshold passed for Signal Failure - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2990 }

farEndBERThresholdPassedForSignalFailureSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End BER threshold passed for Signal Failure - Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3000 }

farEndBERThresholdPassedForSignalDegradeRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End BER threshold passed for Signal Degrade - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3010 }

farEndBERThresholdPassedForSignalDegradeSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End BER threshold passed for Signal Degrade - Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3020 }

apsChannelFarEndProtectionLineSignalDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "APS Channel - Far End Protection Line Signal Degrade."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3030 }

ringSwitchIsActiveOnTheEastSide
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Switch is active on the East Side."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3040 }

ringSwitchIsActiveOnTheWestSide
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Switch is active on the West Side."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3050 }

spanSwitchIsActiveOnTheEastSide
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Span Switch is active on the East Side."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3060 }

spanSwitchIsActiveOnTheWestSide
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Span Switch is active on the West Side."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3070 }

uniDirectionalFullPassThroughIsActive
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Uni-directional Full Pass Through is active."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3080 }

biDirectionalFullPassThroughIsActive
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Bi-directional Full Pass Through is active."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3090 }

kBytesPassThroughIsActive
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "K Bytes Pass Through is active."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3100 }

ringIsSegmented
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring is Segmented."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3110 }

ringTopologyIsUnderConstruction
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Topology is under construction."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3120 }

lockoutOfProtectionAllSpans
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Lockout of Protection - All Spans."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3130 }

farEndOfFiberIsProvisionedWithDifferentRingID
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far end of fiber is provisioned with different ring ID"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3140 }

bothEndsOfFiberProvisionedAsEastOrBothAsWest    
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Both ends of fiber provisioned as East, or both as West"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3150 }

securityInvalidLoginUsernameSeeAuditTrail
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS deprecated
    DESCRIPTION "Security: Invalid Login Username - See Audit Trail"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3160 }

autonomousMessagesInhibited
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Autonomous messages inhibited"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3170 }

trafficStormOnLANLANTemporarilyDisabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Traffic storm on LAN. LAN temporarily disabled."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3180 }

reptdbchgMessagesInhibited
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "REPT^DBCHG messages of TL1 inhibited"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3190 }

securityUserIDHasExpired
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Security: user ID has expired"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3200 }

partialFanFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Partial Fan Failure"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3210 }
forcedSwitchRequestOnRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Force switch request on Ring"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3220 }

forcedSwitchRequestOnSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Force switch request on Span"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3230 }

lockoutSwitchRequestOnRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Lockout switch request on Ring"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3240 }

lockoutSwitchRequestOnSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Lockout switch request on Span"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3250 }

manualSwitchRequestOnRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Manual switch request on Ring"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3260 }

manualSwitchRequestOnSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Manual switch request on Span"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3270 }

communicationFailurePeerToPeerSlotControlBusA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Peer to Peer Slot communication failure - Control Bus A"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3280 }

communicationFailurePeerToPeerSlotControlBusB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Peer to Peer Slot communication failure - Control Bus B"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3290 }

controllerAToShelfSlotCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Controller A to shelf slot communication failure"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3300 }

controllerBToShelfSlotCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Controller B to shelf slot communication failure"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3310 }

interconnectionEquipmentFailureWorkingPayloadBus
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Interconnection Equipment Failure - Working Payload Bus"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3320 }

interconnectionEquipmentFailureProtectPayloadBus
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Interconnection Equipment Failure - Protect Payload Bus"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3330 }

inhibitSwitchToProtectRequestOnEquipment
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Inhibit Switch to Protect Request on equipment"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3340 }

inhibitSwitchToWorkingRequestOnEquipment
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Inhibit Switch to Working Request on equipment"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3350 }

berThresholdExceededForSignalDegradeLine
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Degrade - Line"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3360 }

berThresholdExceededForSignalDegradePath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Degrade - Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3370 }

berThresholdExceededForSignalFailureLine
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold Exceeded For Signal Failure - Line"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3380 }

berThresholdExceededForSignalFailurePath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold Exceeded For Signal Failure - Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3390 }

exercisingRingSuccessfully
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercising Ring Successfully"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3400}

exercisingSpanSuccessfully
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercising Span Successfully"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3410}

spanIsInWaitToRestoreState
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Span is in Wait To Restore state"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3420 }

exerciseRequestOnRingFailed
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercise Ring Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3430 }

exerciseRequestOnSpanFailed
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercise Span Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3440 }

farEndLockoutOfProtectionSpan
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far end Lockout of Protection Channel - Span"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3450 }

manufacturingDataMemoryEEPROMFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Manufacturing EEPROM Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3460 }

replaceableEquipmentOrUnitIsMissing
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Replaceable Equipment/Unit Is Missing"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3470 }

softwareDownloadFailed                  
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Software Download Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3480 }

extraTrafficPCADropped
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extra Traffic Dropped"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3490 }

etherTxOversubscribed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "pkt loss due to oversubscribed xmit"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3500 }

etherRxOverSubscribed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "pkt loss due to oversubscribed rcv"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3510 }

etherTxExcessFlowCtrl
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "excessive ethernet flow ctl xmited"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3520 }

etherRxExcessFlowCtrl
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "excessive ethernet flow ctl recvd"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3530 }

transportLayerFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "transport layer failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3540 }

etherTxUnderrun
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ether hdge internal fifo underrun"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3550 }

synchronizationReferenceFrequencyOutOfBounds
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Synchronization reference frequency out of bounds."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3560 }

ntpOrSntpHostFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "NTP/SNTP Host Failure."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3570 }

peerCardNotResponding
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Peer Card Not Responding"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3580 }

alarmsAndEventsSuppressedForThisObject
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Alarms and events suppressed for this object"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3590 }

ds3FrameFormatMismatch
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DS3 Frame Format Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3600 }

waitToRestore
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Wait To Restore"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3610 }

extremeHighVoltBatteryA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme High Volt Battery A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3620 }

extremeLowVoltBatteryA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme Low Volt Battery A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3630 }

extremeHighVoltBatteryB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme High Volt Battery B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3640 }

extremeLowVoltBatteryB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme Low Volt Battery B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3650 }

iosConfigCopyFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "IOS config copy failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3660 }

iosConfigCopyInProgress
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "IOS config copy in progress"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3670 }

-- Begin: UCP traps

signalingUnableToSetupCircuit
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Signaling Unable to setup circuit"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3710 }

errorInStartupConfig
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Error in Startup Config"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3712 }

noStartupConfig
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "No Startup Config"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3714 }

needToSaveRunningConfig
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Need to Save Running Config"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3716 }

invalidAlarm
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid Alarm"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3718 }

rsvpHelloFSMToNeighborDown
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RSVP Hello FSM to Neighbor down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3720 }

securityInvalidLoginUsername
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Security: Invalid Login - Username - See Audit Log"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3722 }

databaseBackupFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Database Backup Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3724 }

databaseRestoreFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Database Restore Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3726 }

lmpHelloFSMToControlChannelDown
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Hello FSM to Control Channel down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3730 }

lmpNeighborDiscoveryHasFailed
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Neighbor Discovery has failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3740 }

unauthorizedIncomingSignalingRequest
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Unauthorized incoming signaling request"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3750 }

auditLog80PercentFull
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Audit Log 80 Percent Full"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3760 }

moduleCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Module Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3762 }

auditLog100PercentFullOldestRecordsWillBeLost
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Audit Log 100 Percent Full - Oldest records will be lost"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3764 }

standbyDatabaseOutOfSync
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Standby Database Out of Sync"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3766 }

redundantPowerCapabilityLost
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Redundant Power Capability Lost"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3768 }

-- End: UCP traps

forcedSwitchToPrimaryReference
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch To Primary Reference"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3770 }

forcedSwitchToSecondReference
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch To Second Reference"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3780 }

forcedSwitchToThirdReference
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch To Third Reference"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3790 }

forcedSwitchToInternalClock
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch To Internal Clock"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3800 }

industrialHighTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Industrial High Temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3805 }

improperMatrixEquipmentInserted
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Improper matrix equipment inserted"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3810 }

eqptProblemOnCarrierOrPIM
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EQPT problem on Carrier or PIM"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3820 }

eqptProblemOnPIMOrPPM
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EQPT problem on PIM or PPM"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3830 }


-- Begin: SDH traps

timSectionTraceIdentifierMismatchFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "TIM Section - Trace Identifier Mismatch Failure."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4000 }

aisMultiplexSectionAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Multiplex Section - Alarm Indication Signal."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4010 }

rfiMultiplexSectionRemoteFailureOrAlarmIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Multiplex Section - Remote Failure Indication."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4020 }

timHighOrderTraceIdentifierMismatchFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH High Order - Trace Identifier Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4030 }

aisAdministrationUnitAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Administration Unit - Alarm Indication Signal."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4040 }

lopAdministrationUnitLossOfPointer
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Administration Unit - Loss of Pointer."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4050 }

slmfUnequippedHighOrderPathUnequipped
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH SLMF High Order - Unequipped Path."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4060 }

slmfPLMHighOrderPathLabelMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH SLMF High Order - Path Label Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4070 }

rfiHighOrderRemoteFailureOrAlarmIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH High Order - Remote Failure Indication."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4080 }

lopTributaryUnitLossOfPointer
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Tributary Unit - Loss of Pointer."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4090 }

aisTributaryUnitAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Tributary Unit - Alarm Indication Signal."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4100 }

slmfUnequippedLowOrderPathUnequipped
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Low Order - SLMF Unequipped Path."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4110 }

slmfPLMLowOrderPathLabelMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Low Order - SLMF Path Label Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4120 }

timLowOrderTraceIdentifierMismatchFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Low Order - Trace Identifier Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4130 }

rfiLowOrderRemoteFailureOrAlarmIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Low Order - Remote Failure Indication."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4140 }

g811PrimaryReferenceClockTraceable
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "G811 - Primary Reference Clock traceable."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4150 }


g812TransitNodeClockTraceable
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "G812 - Transit Node Clock traceable."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4160 }

g812LocalNodeClockTraceable
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "G812 - Local Node Clock traceable."    
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4170 }

g813SynchronousEquipmentTimingSourceTraceable
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "G813 - Synchronous Equipment Timing Source traceable."    
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4180 }

e1LoopbackDueToFEACCommand
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "loopback due to FEAC Command E1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4190 }

e1LoopbackCommandSentToFarEnd
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "loopback Command sent to Far End E1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4200 }
 
e3LoopbackDueToFEACCommand
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "loopback due to FEAC Command E3"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4210 }

farEndMultipleE1LOSDetectedOnE3
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end Multiple E1 LOS detected on E3"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4220 }

farEndE1EqptFailNonServiceAffecting
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end E1 eqpt fail non service affecting"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4230 }

farEndE1EqptFailServiceAffecting
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end E1 eqpt fail service affecting"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4240 }


farEndSingleE1LOS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end Single E1 LOS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4250 }

farEndE3EqptFailServiceAffecting
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end E3 eqpt fail service affecting"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4260 }
 
e3LoopbackCommandSentToFarEnd
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "loopback Command sent to Far End E3"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4270 }

farEndE3EqptFailNonServiceAffecting
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end E3 eqpt fail non service affecting"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4280 }

lowVoltBatteryA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Low Volt - Battery A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4290 }

highVoltBatteryA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High Volt - Battery A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4300 }

lowVoltBatteryB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Low Volt - Battery B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4310 }

highVoltBatteryB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High Volt - Battery B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4320 }

msspRingOutOfSync
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "MS-SP ring out of sync"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4330 }

msspMultiNodeTableUpdateCompleted
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "MS-SP ring tables resynchronized"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4340 }

automaticSNCPSwitchCausedByAIS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by AIS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4350 }

automaticSNCPSwitchCausedByLOP
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by Lop"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4360 }

automaticSNCPSwitchCausedByUNEQ
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by Uneq"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4370 }
 
automaticSNCPSwitchCausedByPDI
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by PDI"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4380 }

automaticSNCPSwitchCausedBySFBER
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by Sfber"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4390 }

automaticSNCPSwitchCausedBySDBER
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by Sdber"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4400 }

stmConcatenationError
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "concatenation error STM"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4410 }

e3IdleCondition
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "idle Condition E3"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4420 }

channelMSSPInconsistentAPSCode
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "channel MSSP inconsistent APS code"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4430 }

channelMSSPImproperAPSCodeAPS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "channel MSSP Improper APS code APS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4440 }

channelMSSPNodeIdMismatchAPS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "channel MSSP Node Id Mismatch APS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4450 }

channelMSSPDefaultKAPS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "channel MSSP Default K APS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4460 }

channelMSSPConnectionLossAPS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "channel MSSP Connection loss APS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4470 }

minimumClockTraceableSDH
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Minimum clock Traceable"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4480 }

lineIsInWaitToRestoreStateSDH
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH line is in Wait To Restore state "
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4490 }

berThresholdExceededForSignalDegradeHighOrder
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Degrade - High Order"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4500 }

berThresholdExceededForSignalFailureHighOrder
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Failure - High Order"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4510 }

berThresholdExceededForSignalDegradeLowOrder
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Degrade - Low Order"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4520 }

berThresholdExceededForSignalFailureLowOrder
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Failure - Low Order"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4530 }

failureToSwitchToProtectionHighOrderPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Failure To Switch To Protection - High Order Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4540 }

failureToSwitchToProtectionLowOrderPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Failure To Switch To Protection - Low Order Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4550 }
    
lofAdministrationUnitLossOfMultiFrame
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Administration Unit Loss of Multiframe."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4560 }

sdhSpanIsInWaitToRestoreState
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH span is in Wait To Restore state"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4570 }

a8b10bOutOfSync
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "8B10B Out of Sync"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4755 }

odukPMAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4760 }

otukAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUk: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4765 }

otukSMBackwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUk: Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4770 }

fecUncorrectedWord
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "FEC Uncorrected Word"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4780 }

gccTerminationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4785 }

otukIncomingAlignmentError
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUk: Incoming Alignment Error"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4790 }

odukLockedDefectPM
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: Locked Defect PM"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4795 }

lossOfMultiFrame
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Multi-Frame"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4800 }

odukOpenConnectionIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: Open Connection Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4805 }

payloadTypeIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Payload Type Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4810 }

odukTrailTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: Trail Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4815 }

otukTrailTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUk: Trail Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4820 }

equipmentHighLaserBias
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Laser Bias"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4825 }

equipmentHighLaserTemp
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Laser Temp"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4830 }

equipmentHighLaserPeltier
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Laser Peltier"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4835 }

equipmentHighRxPower
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Rx power"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4840 }

equipmentHighTxPower
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Tx power"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4845 }

equipmentHighTransceiverVoltage
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Transceiver voltage"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4850 }

equipmentLowLaserBias
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Laser Bias"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4855 }

equipmentLowLaserTemp
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Laser Temp"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4860 }

equipmentLowLaserPeltier
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Laser Peltier "
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4865 }

equipmentLowRxPower
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Rx power"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4870 }

equipmentLowTxPower
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Tx power"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4875 }

equipmentLowTransceiverVoltage
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Transceiver voltage"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4880 }

equipmentRxLocked
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Rx Locked"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4885 }

equipmentSquelched
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Squelched"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4890 }

equipmentTxLocked
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Tx Locked"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4895 }

otukSignalFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUK Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4900 }

odukSignalFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUK Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4905 }

otukSignalDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUK Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4910 }

odukSignalDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUK Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4915 }

pluggablePortMissing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Pluggable Port missing"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4920 }

pluggablePortRateMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Pluggable Port rate mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4925 }

pluggablePortSecurityCodeMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Pluggable Port security code mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4930 }

tciNotSelected
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Tci not selected"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4935 }

tci1ClockFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Tci 1 Clock Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4940 }

odukPMBackwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: PM Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4945 }

odukTCM1BackwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: TCM1 Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4950 }

odukTCM2BackwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: TCM2 Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4955 }

equipmentHighRxTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Rx temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4960 }

equipmentLowRxTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Rx temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4965 }

tci2ClockFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Tci 2 Clock Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4970 }

equipmentWavelengthMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Wavelength Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4975 }

dspCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DSP Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4980 }

dspFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DSP Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4985 }
laserApproachingEndOfLife
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser Approaching End of Life"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5000 }

crossconnectLoopback
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Cross-connect Loopback"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5010 }

adminLogoutOfUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Admin Logout of User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5020 }

userLockedOut
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "User Locked Out"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5030 }

adminLockoutOfUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Admin Lockout of User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5040 }

adminLockoutClear
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Admin Lockout Clear"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5050 }

invalidLoginUsername
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid Login: Username"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5060 }

securityInvalidLoginPassword
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid Login: Password"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5070 }

securityInvalidLoginLockedOut
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid Login: Locked Out"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5080 }

securityInvalidLoginAlreadyLoggedOn
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid Login: Already Logged On"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5090 }

loginOfUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Login of User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5100 }

automaticLogoutOfIdleUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Logout of IdleUser"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5110 }

logoutOfUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Logout of User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5120 }

enhancedRemoteFailureIndicationPathServer
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Enhanced Remote Failure Indication - Path - Server"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5200 }

enhancedRemoteFailureIndicationPathConnectivity
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Enhanced Remote Failure Indication - Path - Connectivity"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5210 }

enhancedRemoteFailureIndicationPathPayload
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Enhanced Remote Failure Indication - Path - Payload"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5220 }

firewallHasBeenDisabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Firewall Has Been Disabled"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5230 }

securityIntrusionDetPwd
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Security Intrusion - Incorrect Password"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5240 }

securityIntrusionDetUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Security Intrusion - Incorrect Username"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5250 }

    connectionEquipmentMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Connection Equipment Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5260 }

disableInactiveUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Disable Inactive User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5270 }

disableInactiveClear
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Disable Inactive Clear"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5280 }

batteryFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Battery Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5290 }

extremeHighVolt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme High Volt"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5300 }

extremeLowVolt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme Low Volt"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5310 }

highVolt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High Volt"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5320 }

lowVolt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Low Volt"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5330 }

suspendUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Suspend User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5340 }

suspendUserClear
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Suspend User Clear"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5350 }

lineDccTerminationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Line DCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5360 }

multiplexSectionDccTerminationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Multiplex Section DCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5370 }

gigaBitEthernetOutOfSync
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GigaBit Ethernet Out of Sync"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5380 }

sequenceMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Sequence Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5390 }

lossOfAlignment
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Alignment"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5400 }

outOfUseByAdministrativeCommand
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Out of Use - Administrative Command"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5410 }

outOfUseTransportFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Out of Use - Transport Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5420 }

vcatGroupDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "VCAT Group Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5430 }

vcatGroupDegraded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "VCAT Group Degraded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5440 }

vcatGroupIncomplete
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "VCAT Group Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5450 }

alarmIndicationSignalInTX
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Alarm Indication Signal in TX"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5460 }

remoteAlarmIndicationInTX
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Remote Alarm Indication in TX"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5470 }

kByteAPSChannelFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Kbyte Channel Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5480 }

apsInvalidMode
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "APS Invalid Mode"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5490 }

ipAddressAlreadyInUseWithinTheSameDccArea
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "IP address already in use within the same DCC Area"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5500 }

nodeNameInUseWithinTheSameDccArea
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Node name already in use within the same DCC Area"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5510 }

rearPanelEthernetLinkRemoved
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Rear Panel Ethernet Link Removed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5520 }

manualSwitchToProtectResultedInNoTrafficSwitch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Manual Switch To Protect Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5530 }

manualSwitchBackToWorkingResultedInNoTrafficSwitch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Manual Switch Back To Working Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5540 }

forcedSwitchToProtectResultedInNoTrafficSwitch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch To Protection Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5550 }

forcedSwitchBackToWorkingResultedInNoTrafficSwitch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch Back To Working Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5560 }

duplicateSerialNumberDetectedOnAPluggableEntity
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Duplicate Serial number detected on a pluggable entity"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5570 }

lossOfSignalForOpticalChannel
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Incoming Payload Signal Absent"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5600 }

encapsulationMismatchPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Encapsulation Type Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5610 }

encapsulationMismatchVT
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Encapsulation Mismatch - VT"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5620 }

encapsulationMismatchHighOrderPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Encapsulation Mismatch High Order - Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5630 }

encapsulationMismatchLowOrderPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Encapsulation Mismatch Low Order - Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5640 }

gfpUserPayloadMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP User Payload Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5650 }

gfpFibreChannelDistanceExtensionMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Fibre Channel Distance Extension Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5660 }

gfpFibreChannelDistanceExtensionBufferStarvation
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Fibre Channel Distance Extension Buffer Starvation"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5670 }



gfpFibreChannelDistanceExtensionCreditStarvation
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Fibre Channel Distance Extension Credit Starvation"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5680 }

automaticWdmAnsFinished
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic WDM ANS Finished"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5690 }

gfpClientSignalFailDetected
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Client Signal Fail Detected"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5700 }

gfpLossOfFrameDelineation
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Loss of Frame Delineation"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5710 }

gfpExtensionHeaderMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Extension Header Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5730 }

incomingOverheadSignalAbsent
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Signal for Overhead"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5740 }

opticalSafetyRemoteInterlockOn
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Safety Remote Interlock On"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5750 }

automaticPowerControlCorrectionSkipped
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Power Control Correction Skipped"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5770 }

apcCannotSetValueDueToRangeLimits
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "APC cannot set value due to range limits"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5780 }

lcasVcgMemberTxSideInAddState
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS VCG Member Tx Side In ADD State"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5790 }
    
farEndManualSwitchBackToWorkingSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Manual Switch Back to Working - Span"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5800 }

farEndForcedSwitchBackToWorkingSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Forced Switch Back to Working - Span"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5810 }

universalTransponderModuleHardwareFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Universal Transponder Module Hardware Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5820 }

universalTransponderModuleCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Universal Transponder Module Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5830 }

pluginModuleRangeSettingsMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Plug-in Module Range Settings Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5840 }

lcasVcgMemberTxSideInDnuState
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS VCG Member Tx Side In DNU State"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5850 }

lcasControlWordCrcCheckFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS Control Word CRC Check Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5860 }

lcasVcgMemberRxSideInFailState
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS VCG Member Rx Side In FAIL State"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5870 }

signalLossOnDataInterface
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Signal Loss on Data Interface"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5880 }

synchronizationLossOnDataInterface
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Synchronization Loss on Data Interface"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5890 }

portFAIL
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "PORT FAIL"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5900 }

unreachablePortTargetPower
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Unreachable port target power"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5910 }

portAddPowerDegradeLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Port Add Power Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5920 }

portAddPowerDegradeHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Port Add Power Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5930 }

portAddPowerFailLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Port Add Power Fail Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5940 }

portAddPowerFailHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Port Add Power Fail High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5950 }


automaticPowerControlTerminatedOnManualRequest
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Power Control Terminated on Manual request"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6000 }

oduk1AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk-1: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6010 }

oduk2AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk-2: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6020 }

oduk3AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk-3: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6030 }

oduk4AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk-4: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6040 }

temperatureReadingMismatchBetweenSCCards
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Temperature Reading Mismatch Between SC Cards"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6050 }

voltageReadingMismatchBetweenSCCards
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Voltage Reading Mismatch Between SC Cards"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6060 }

alarmsSuppressedonOutOfGroupVcatMember
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Alarms Suppressed on Out-Of-Group VCAT Member"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6070 }

blsrSoftwareVersionMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BLSR Software Version Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6080 }

optimized1Plus1ApsPrimaryFacility
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optimized 1+1 APS Primary Facility"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6090 }

optimized1Plus1ApsPrimarySectionMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optimized 1+1 APS Primary Section Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6100 }

optimized1Plus1ApsInvalidPrimarySection
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optimized 1+1 APS Invalid Primary Section"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6110 }

compositeClockHighLineVoltage
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Composite Clock High Line Voltage"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6120 }

berThresholdExceededForSignalDegradeVt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold Exceeded For Signal Degrade - VT"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6130 }

berThresholdExceededForSignalFailureVt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold Exceeded For Signal Failure - VT"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6140 }

spanLengthOutOfRange
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Span Length Out of Range"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6150 }

idleSignalCondition
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Idle Signal Condition"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6170 }

idleSignalConditionInTx
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Idle Signal Condition in TX"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6180 }

vtPathTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "VT Path Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6190 }

lossOfFrameInTX
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Frame in TX"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6200 }

provisioningMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Provisioning Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6210 }

sectionTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Section Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6220 }

regeneratorSectionTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Regenerator Section Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6230 }

switchingMatrixModuleFailureWorking
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Switching Matrix Module Failure - Working"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6240 }

switchingMatrixModuleFailureProtect
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Switching Matrix Module Failure - Protect"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6250 }

slotCommunicationDisabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Slot Communication Disabled"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6260 }

sessionTimeLimitExpired
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Session Time Limit Expired"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6270 }

userPasswordChangeRequired
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "User Password Change Required"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6280 }

isisAdjacencyFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ISIS Adjacency Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6290 }

msspSoftwareVersionMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "MSSP Software Version Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6300 }

remoteAuthenticationFailSeeAuditLog
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Remote Authentication Fail - See Audit Log"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6310 }

illegalRouteAdditionToNetwork
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Illegal route addition to the Network"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6320 }

ringIsSquelchingStsTraffic
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Is Squelching STS Traffic"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6330 }

ringIsSquelchingVtTraffic
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Is Squelching VT Traffic"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6340 }

archiveOfAuditLogFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Archival of Audit Log Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6350 }

rprWrapped
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Wrapped"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6360 }

shelfCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Shelf Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6370 }

duplicatedShelfIdentifier
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Duplicated Shelf Identifier"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6380 }

softwareMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Software Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6390 }

lmpFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6400 }

opticalTerminationIncomplete
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Termination Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6410 }

forwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6420 }

payloadMissingIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Payload Missing Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6430 }

spanMeasurementCannotBePerformed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Span loss not checked"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6440 }

ringIsSquelchingHighOrderTraffic
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Is Squelching Higher Order Traffic"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6450 }

ringIsSquelchingLowOrderTraffic
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Is Squelching Lower Order Traffic"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6460 }

badPacketCountExceedsThreshold
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Bad Packet Count Exceeds Threshold"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6470 }

linkLayerKeepAliveFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Link Layer Keep-Alive Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6480 }

autonegotiationRemoteFailureIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Auto-Negotiation Remote Failure Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6490 }

trailSignalFail
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Trail Signal Fail"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6500 }

ds1LoopbackCommandSentToFarEnd
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DS1 Loopback Command Sent To Far End"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6510 }

multiplexSectionSignalDegraded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Multiplex Section - Signal Degraded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6520 }

multiplexSectionExcessiveErrors
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Multiplex Section - Excessive Errors"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6530 }

highOrderPathSignalDegraded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High Order Path - Signal Degraded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6540 }

highOrderPathExcessiveErrors
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High Order Path - Excessive Errors"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6550 }

lowOrderPathSignalDegraded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Low Order Path - Signal Degraded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6560 }

lowOrderPathExcessiveErrors
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Low Order Path - Excessive Errors"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6570 }

regeneratorSectionDccTerminationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Regenerator Section - DCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6580 }

networkMemoryPoolLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Network Memory Pool Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6590 }

ospfRoutingTableOverflow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OSPF Routing Table Overflow"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6600 }

autoLaserShutdownDisabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Auto Laser Shutdown Disabled"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6610 }

wavelengthOutOfLock
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Wavelength Out of Lock"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6620 }

rprProtectionIsActive
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Protection Is Active"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6630 }

maxRPRStationNumberExceeded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Max RPR Station Number Exceeded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6640 }

rprProtectionConfigurationMismatched
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Protection Configuration Mismatched"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6650 }

reservedBandwidthLinkRateExceededOnRinglet0
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Reserved Bandwidth Link Rate Exceeded On Ringlet0"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6660 }

reservedBandwidthLinkRateExceededOnRinglet1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Reserved Bandwidth Link Rate Exceeded On Ringlet1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6670 }

rprInterfaceInPassThroughMode
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Interface In Pass Through Mode"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6680 }

rprPeerNodeIsMissing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Peer Node is Missing"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6690 }

rprRiFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR RI Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6700 }

rprSignalFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6710 }

rprSignalDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6720 }

interlinkFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ADM Peer Cards Interlink Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6730 }

apcWrongGain
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "APC Wrong Gain Set Point"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6740 }

rprSpanMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Span Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6750 }

fastAutomaticProtectionSwitching
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Fast Automatic Protection Switching"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6840 }

fastAutomaticProtectionSwitchingConfigMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Fast Automatic Protection Switching Config Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6850 }

lcasSinkGroupError
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS Sink Group Error"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6860 }

lcasVCGMemberRxSideInDNUState
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS VCG Member Rx Side In DNU State"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6870 }

fcDistanceExtFuncNotEstablished
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION " Fibre Channel Distance Extension Function Not Established"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6880 }

nonCiscoPPMInserted
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Non Cisco PPM Inserted"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6890 }

unqualifiedPPMInserted
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Unqualified PPM Inserted"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6900 }

ftaMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "FanTray Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6910 }

cardPortsUnableToProvideProtection
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Card/Ports Unable To Provide Protection"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6920 }

lmpSignalDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6930 }

lmpSignalFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6940 }

lmpUnallocatedDataLink
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Unallocated Data Link"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6950 }

frontPortLinkLoss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "TCC Front Port Link Loss"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6960 }

bertEnabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BERT Enabled "
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6970 }

bertSynchronizationStatusFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BERT Synchronization Status Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6975 }

workQueueFull
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Work Queue Full"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6980 }

equipmentPowerFailureAtConnectorA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Power Failure At Connector A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7000 }

equipmentPowerFailureAtConnectorB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Power Failure At Connector B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7005 }

equipmentPowerFailureAtReturnConnectorA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Power Failure At Return Connector A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7010 }

equipmentPowerFailureAtReturnConnectorB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Power Failure At Return Connector B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7015 }

loginFailThresholdExceeded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid login attempt threshold exceeded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7020 }

connectionIdMismatchOnMatrixA
  NOTIFICATION-TYPE
    OBJECTS {
      cerentGenericNodeTime,
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Connection ID mismatch on Matrix A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7025 }

connectionIdMismatchOnMatrixB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Connection ID mismatch on Matrix B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7030 }

manufacturingEepromFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS deprecated 
    DESCRIPTION "Manufacturing data memory (EEPROM) failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7035 }

equipmentFailureHighTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment failure high temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7040 }

laserBiasCurrentHigh                         
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser bias current high"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7045 }

highLaserTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High laser temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7050 }

bridgeAndRollHasOccurred
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Bridge and Roll Has Occurred"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7055 }

bridgeAndRollIsPendingAValidSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Bridge and Roll is Pending a Valid Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7060 }

airFlow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS deprecated
    DESCRIPTION "Air Flow"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7065 }

partialFanFailurePartsFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Partial Fan Failure - Parts Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7070 }

unprotectedSyncronizationEquipment
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Unprotected Synchronization Equipment"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7075 }

unprotectedMatrixEquipment
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Unprotected Matrix Equipment"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7080 }

matrixEquipmentUnavailable
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Matrix Equipment Unavailable"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7085 }

controlBusFailureTscA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Control Bus Failure - TSC A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7090 }

controlBusFailureTscB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Control Bus Failure - TSC B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7095 }

payloadBusFailureMatrixA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Payload Bus Failure - Matrix A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7100 }

payloadBusFailureMatrixB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Payload Bus Failure - Matrix B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7105 }

matrixOperationSuspended
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Matrix Operation Suspended"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7110 }

clockFailureTsc
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Clock Module Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7115 }

payloadLoopback
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loopback - Payload"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7120 }

dccChannelLoss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DCC Channel Loss"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7125 }

reptPmMsgInhibited


  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Autonomous PM Report Message Inhibited"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7130 }

loopbackCrs
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loopback - Cross Connect"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7135 }

syncRefFreqOutOfBound
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Synchronization Reference Frequency Out Of Bounds"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7140 }

systemUpgradeInProgress
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "System Upgrade In Progress"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7145 }

eqptFailToBoot
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Fails To Boot"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7150 }

eqptPowerFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Power Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7155 }

clockBusFailureTscA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Clock Bus Failure - Shelf Controller A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7160 }

clockBusFailureTscB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Clock Bus Failure - Shelf Controller B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7165 }

powerFuseFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Power Fuse Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7170 }

controlCommunicationsEquipmentFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Control Communication Equipment Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7175 }

differentSoftwareVersion
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Different Software Version"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7180 }

ospfHelloFail
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OSPF Hello Fail"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7185 }

clockModuleFrequencyMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Clock Module Frequency Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7190 }

etherPortSwitch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "TSC switched to alternate ethernet port"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7195 }

openIOSlots
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Open IO Slot(s)"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7200 }

equipmentBootInProgress
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment boot in-progress."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7205 }

lossOfClockFromMateShelfController
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Clock from mate Shelf Controller"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7210 }

dcuLossFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DCU Loss Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7230 }

ochncMaintenance
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OCHNC Maintenance"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7235 }
	
alarmIndicationSignalInTXCustomerInstallation
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Alarm Indication Signal In Tx Customer Installation"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7435 }

remoteAlarmIndicationInTXCustomerInstallation
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Remote Alarm Indication In Tx Customer Installation"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7440 }

odukTCM1AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Alarm Indication Signal TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13100 }

odukTCM2AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Alarm Indication Signal TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13105 }

odukLockedDefectTCM1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Locked Defect - TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13110 }

odukLockedDefectTCM2
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Locked Defect - TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13115 }

otukLossOfFrame
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUk: Loss Of Frame"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13120 }

odukOpenConnectionIndicationTCM1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Open Connection Indication TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13125 }

odukOpenConnectionIndicationTCM2
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Open Connection Indication TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13130 }

odukTrailTraceIdentifierMismatchTCM1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Trail Trace Identifier Mismatch TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13135 }

odukTrailTraceIdentifierMismatchTCM2
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Trail Trace Identifier Mismatch TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13140 }

odukSignalFailureTCM1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Signal Failure - TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13145 }

odukSignalFailureTCM2
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Signal Failure - TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13150 }

odukSignalDegradeTCM1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Signal Degrade - TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13155 }

odukSignalDegradeTCM2
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Signal Degrade - TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13160 }

lossOfChannel
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Channel"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13165 }

fecMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "FEC Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13170 }

    timSectionMonitorTraceIdentifierMismatchFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "TIM Section Monitor - Trace Identifier Mismatch Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13175 }

automaticLaserShutdown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Laser Shutdown"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13180 }

shutterInsertionLossVariationDegradeLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Shutter Insertion Loss Variation Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13200 }

    opticalChannelDeactivationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Channel de-activation failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13205 }

shutterInsertionLossVariationDegradeHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Shutter Insertion Loss Variation Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13210 }

networkTopologyIncomplete
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Network Topology Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13215 }

pluginModuleCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Plug-in Module Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13220 }

opticalNetworkTypeMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Network Type Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13225 }

opticalPowerDegradeLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser Power Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13230 }

automaticPowerControlFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Power Control Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13235 }

opticalPowerDegradeHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Power Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13240 }

automaticPowerControlDisabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Power Control Disabled"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13245 }

opticalPowerFailureLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Power Failure Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13250 }

ringIdMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Id Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13255 }

opticalPowerFailureHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Power Failure High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13260 }

lossOfContinuity
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss Of Continuity"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13270 }

variableOpticalAttenuatorDegradeLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Variable Optical Attenuator Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13280 }

variableOpticalAttenuatorDegradeHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Variable Optical Attenuator Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13290 }

variableOpticalAttenuatorFailureLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Variable Optical Attenuator Failure Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13300 }

variableOpticalAttenuatorFailureHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Variable Optical Attenuator Failure High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13310 }

laserBiasDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser Bias Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13320 }

laserBiasFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "aser Bias Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13330 }

laserTemperatureDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13340 }

opticalAmplifierGainDegradeLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Amplifier Gain Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13350 }

opticalAmplifierGainDegradeHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Amplifier Gain Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13360 }

opticalAmplifierGainFailureLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Amplifier Gain Failure Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13370 }

opticalAmplifierGainFailureHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Amplifier Gain Failure High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13380 }

opticalChannelConnectionFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Channel connection failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13390 }

opticalChannelIncomplete
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Channel Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13395 }

opticalChannelActivationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Channel activation failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13400 }

laserAutoPowerReduction
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser Auto Power Reduction"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13410 }

caseTemperatureDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Case Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13420 }

fiberTemperatureDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Fiber Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13430 }

shutterOpen
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Shutter Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13440 }

awgTemperatureDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "AWG Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13450 }

awgTemperatureFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "AWG Temperature Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13460 }

awgOverTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "AWG Over-Temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13470 }

opticalAmplifierInitialization
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Amplifier Initialization"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13480 }

awgWarmUp
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "AWG Warm Up"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13490 }

incSigloss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Incoming Signal Loss on Fibre Channel Interface"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13510 }

incSyncloss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Incoming Synchronization Loss on Fibre Channel Interface"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13515 }

incGfpOutOfFrame
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Out Of Frame Detected by GFP Receiver"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13520 }

incGfpSigLoss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Client Signal Loss Frames Detected by GFP Receiver"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13525 }

incGfpSyncLoss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Client Sychronization Loss Frames Detected by GFP Receiver"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13530 }

nodeGenericGroup OBJECT-GROUP
        OBJECTS { 
          cerentGenericSoftwareVersion }
        STATUS current
        DESCRIPTION
          "The group for node related objects"
        ::= { cerentGenericGroups 10 }
        
alarmGenericGroup OBJECT-GROUP
        OBJECTS {
          cerentGenericAlarmCount,
          cerentGenericAlarmObjectIndex,
          cerentGenericAlarmObjectType,
          cerentGenericAlarmSlotNumber,
          cerentGenericAlarmPortNumber,
          cerentGenericAlarmLineNumber,
          cerentGenericAlarmType,
          cerentGenericAlarmState,
          cerentGenericAlarmTimeStamp,
          cerentGenericAlarmObjectName,
          cerentGenericAlarmAdditionalInfo,
          cerentGenericAlarmSeverity,
          cerentGenericAlarmStatus,
          cerentGenericAlarmServiceAffecting
        }
        STATUS current
        DESCRIPTION
          "The group for node related objects"
        ::= { cerentGenericGroups 20 }
        
eventGenericGroup NOTIFICATION-GROUP
     NOTIFICATIONS {
       alarmUnknown,
       alarmCutoffIsInManualMode,
       failureDetectedExternalToTheNE,
       externalError,
       excessiveSwitching,
       sdccTerminationFailure,
       incomingFailureCondition,
       alarmIndicationSignal,
       alarmIndicationSignalLine,
       alarmIndicationSignalPath,
       alarmIndicationSignalVT,
       apsChannelFailure,
       channelByteFailureAPS,
       channelProtectionSwitchingChannelMatchFailureAPS,
       channelAutomaticProtectionSwitchModeMismatchAPS,
       farEndProtectionLineFailure,
       inconsistentAPSCode,
       improperAPSCode,
       nodeIdMismatch,
       channelDefaultKAPS,
       connectionLoss,
       bipolarViolation,
       carrierLossOnTheLAN,
       concatenationErrorSTS,
       excessCollisionsOnTheLAN,
       facilityFailure,
       farEndAIS,
       farEndMultipleDS1LOSDetectedOnDS3,
       farEndDS1EqptFailNonServiceAffecting,
       farEndDS1EqptFailServiceAffecting,
       farEndSingleDS1LOS,
       farEndDS3EqptFailNonServiceAffecting,
       farEndDS3EqptFailServiceAffecting,
       farEndCommonEquipmentFailureNonServiceAffecting,
       farEndIDLE,
       farEndLOS,
       farEndLOF,
       farEndBlockError,
       ds3IdleCondition,
       lossOfFrame,
       lossOfPointer,
       lossOfPointerPath,
       lossOfPointerVT,
       lossOfSignal,
       outOfFrame,
       pathSelectorFailure,
       remoteAlarmIndication,
       remoteFailureIndication,
       remoteFailureIndicationLine,
       remoteFailureIndicationPath,
       remoteFailureIndicationVT,
       signalDegrade,
       severelyErroredFrame,
       signalFailure,
       signalLabelMismatchFailure,
       payloadDefectIndication,
       payloadDefectIndicationPath,
       payloadLabelMismatchPath,
       signalLabelMismatchFailurePayloadLabelMismatchVT,
       unequippedPath,
       signalLabelMismatchFailureUnequippedVT,
       lossOfSynchronization,
       outOfSynchronization,
       primarySynchronizationReferenceFailure,
       secondarySynchronizationReferenceFailure,
       thirdSynchronizationReferenceFailure,
       fourthSynchronizationReferenceFailure,
       fifthSynchronizationReferenceFailure,
       sixthSynchronizationReferenceFailure,
       failedToReceiveSynchronizationStatusMessage,
       synchronizationStatusMessagesAreDisabledOnThisInterface,
       stratum1PrimaryReferenceSourceTraceable,
       synchronizedTraceabilityUnknown,
       stratum2Traceable,
       transitNodeClockTraceable,
       stratum3ETraceable,
       stratum3Traceable,
       sonetMinimumClockTraceable,
       stratum4Traceable,
       doNotUseForSynchronization,
       reservedForNetworkSynchronizationUse,
       outgoingFailureCondition,
       remoteDefectIndicationLine,
       remoteDefectIndicationPath,
       freeRunningSynchronizationMode,
       holdoverSynchronizationMode,
       fastStartSynchronizationMode,
       internalFault,
       internalError,
       internalMessageError,
       mismatchOfEquipmentAndAttributes,
       watchdogTimerTimeout,
       softwareFaultOrFailure,
       softwareFaultDataIntegrityFault,
       programFailure,
       controlEquipmentFailure,
       primaryNonVolatileBackupMemoryFailure,
       secondaryNonVolatileBackupMemoryFailure,
       controlBusFailure,
       controlBus1Failure,
       controlBus2Failure,
       tccAToShelfSlot1DROP1CommunicationFailure,
       tccAToShelfSlot2DROP2CommunicationFailure,
       tccAToShelfSlot3DROP3CommunicationFailure,
       tccAToShelfSlot4DROP4CommunicationFailure,
       tccAToShelfSlot5TRUNK1CommunicationFailure,
       tccAToShelfSlot6TRUNK2CommunicationFailure,
       tccAToShelfSlot7TCCACommunicationFailure,
       tccAToShelfSlot8XCONACommunicationFailure,
       tccAToShelfSlot9AICCommunicationFailure,
       tccAToShelfSlot10XCONBCommunicationFailure,
       tccAToShelfSlot11TCCBCommunicationFailure,
       tccAToShelfSlot12TRUNK3CommunicationFailure,
       tccAToShelfSlot13TRUNK4CommunicationFailure,
       tccAToShelfSlot14DROP5CommunicationFailure,
       tccAToShelfSlot15DROP6CommunicationFailure,
       tccAToShelfSlot16DROP7CommunicationFailure,
       tccAToShelfSlot17DROP8CommunicationFailure,
       tccAToDCCAProcessorCommunicationFailure,
       tccBToShelfSlot1DROP1CommunicationFailure,
       tccBToShelfSlot2DROP2CommunicationFailure,
       tccBToShelfSlot3DROP3CommunicationFailure,
       tccBToShelfSlot4DROP4CommunicationFailure,
       tccBToShelfSlot5TRUNK1CommunicationFailure,
       tccBToShelfSlot6TRUNK2CommunicationFailure,
       tccBToShelfSlot7TCCACommunicationFailure,
       tccBToShelfSlot8XCONACommunicationFailure,
       tccBToShelfSlot9AICCommunicationFailure,
       tccBToShelfSlot10XCONBCommunicationFailure,
       tccBToShelfSlot11TCCBCommunicationFailure,
       tccBToShelfSlot12TRUNK3CommunicationFailure,
       tccBToShelfSlot13TRUNK4CommunicationFailure,
       tccBToShelfSlot14DROP5CommunicationFailure,
       tccBToShelfSlot15DROP6CommunicationFailure,
       tccBToShelfSlot16DROP7CommunicationFailure,
       tccBToShelfSlot17DROP8CommunicationFailure,
       tccBToDCCBProcessorCommunicationFailure,
       controlProcessorFailure,
       workingMemoryFailure,
       interconnectionEquipmentFailure,
       payloadBusFailureToIOSlot1XCONSlot8,
       payloadBusFailureToIOSlot2XCONSlot8,
       payloadBusFailureToIOSlot3XCONSlot8,
       payloadBusFailureToIOSlot4XCONSlot8,
       payloadBusFailureToIOSlot5XCONSlot8,
       payloadBusFailureToIOSlot6XCONSlot8,
       payloadBusFailureToIOSlot12XCONSlot8,
       payloadBusFailureToIOSlot13XCONSlot8,
       payloadBusFailureToIOSlot14XCONSlot8,
       payloadBusFailureToIOSlot15XCONSlot8,
       payloadBusFailureToIOSlot16XCONSlot8,
       payloadBusFailureToIOSlot17XCONSlot8,
       payloadBusFailureToIOSlot1XCONSlot10,
       payloadBusFailureToIOSlot2XCONSlot10,
       payloadBusFailureToIOSlot3XCONSlot10,
       payloadBusFailureToIOSlot4XCONSlot10,
       payloadBusFailureToIOSlot5XCONSlot10,
       payloadBusFailureToIOSlot6XCONSlot10,
       payloadBusFailureToIOSlot12XCONSlot10,
       payloadBusFailureToIOSlot13XCONSlot10,
       payloadBusFailureToIOSlot14XCONSlot10,
       payloadBusFailureToIOSlot15XCONSlot10,
       payloadBusFailureToIOSlot16XCONSlot10,
       payloadBusFailureToIOSlot17XCONSlot10,
       timeSlotInterchangeEquipmentFailure,
       equipmentFailure,
       highTemperature,
       invalidMACAddress,
       boardFailure,
       diagnosticFailure,
       mediumAccessControlFailure,
       facilityTerminationEquipmentFailure,
       automaticLaserShutoffDueToHighTemperature,
       failureToReleaseFromProtection,
       receiverFailure,
       transmitFailure,
       facilityTerminationEquipmentReceiverMissing,
       facilityTerminationEquipmentTransmitterMissing,
       failureToSwitchToProtection,
       failureToSwitchToProtectionRing,
       failureToSwitchToProtectionSpan,
       failureToSwitchToProtectionPath,
       fanFailure,
       equipmentUnitPlugIn,
       nePowerFailureAtConnector,
       fuseAlarm,
       synchronizationUnitFailure,
       synchronizationSwitchingEquipmentFailure,
       equipmentUnitUnplugged,
       loopback,
       ds1LoopbackDueToFEACCommand,
       loopbackCommandSentToFarEndDS1,
       ds3LoopbackDueToFEACCommand,
       ds3LoopbackCommandSentToFarEnd,
       ds2LoopbackDueToFarEndCommand,
       ds2LoopbackCommandSentToFarEnd,
       facilityLoopback,
       networkLoopback,
       terminalLoopback,
       manuallyCausedAbnormalCondition,
       ethernetBridgeIsNewRootOfSpanningTree,
       ethernetBridgeTopologyChange,
       normalCondition,
       embeddedOperationsChannelFailureLinkDown,
       peerStateMismatch,
       proceduralError,
       improperRemoval,
       duplicateNodeID,
       blsrOutOfSync,
       blsrMultiNodeTableUpdateCompleted,
       protectionUnitNotAvailable,
       performanceMonitorThresholdCrossingAlert,
       protectionSwitch,
       recoveryOrServiceProtectionActionHasBeenInitiated,
       automaticSystemReset,
       automaticUPSRSwitchCausedByAIS,
       automaticUPSRSwitchCausedByLOP,
       automaticUPSRSwitchCausedByUNEQ,
       automaticUPSRSwitchCausedByPDI,
       automaticUPSRSwitchCausedBySFBER,
       automaticUPSRSwitchCausedBySDBER,
       coldRestart,
       forcedSwitchBackToWorking,
       forcedSwitchBackToWorkingRing,
       forcedSwitchBackToWorkingSpan,
       forcedSwitchToProtection,
       forcedSwitchToProtectionRing,
       forcedSwitchToProtectionSpan,
       workingFacilityOrEquipmentForcedToSwitchToProtectionPath,
       initializationInitiated,
       lockoutOfProtection,
       lockoutOfProtectionRing,
       lockoutOfProtectionSpan,
       lockoutOfProtectionPath,
       lockoutOfWorking,
       lockoutOfWorkingRing,
       lockoutOfWorkingSpan,
       manualSystemReset,
       manualSwitchToInternalClock,
       manualSwitchToPrimaryReference,
       manualSwitchToSecondReference,
       manualSwitchToThirdReference,
       manualSwitchToFourthReference,
       manualSwitchToFifthReference,
       manualSwitchToSixthReference,
       manualSwitchBackToWorking,
       manualSwitchBackToWorkingRing,
       manualSwitchBackToWorkingSpan,
       manualSwitchToProtection,
       manualSwitchToProtectionRing,
       manualSwitchToProtectionSpan,
       manualSwitchOfWorkingFacilityOrEquipmentToProtectionPath,
       powerfailRestart,
       ringIsSquelchingTraffic,
       softwareDownloadInProgress,
       switchToInternalClock,
       switchToPrimaryReference,
       switchToSecondReference,
       switchToThirdReference,
       switchToFourthReference,
       switchToFifthReference,
       switchToSixthReference,
       systemReboot,
       switchedBackToWorking,
       switchedToProtection,
       warmRestart,
       ringIsInWaitToRestoreState,
       manualSwitchRequest,
       forcedSwitchRequest,
       lockoutSwitchRequest,

       rmonHistoriesAndAlarmsResetReboot,
       rmonThresholdCrossingAlarm,
       alarmsSuppressedByUserCommand,
       alarmsSuppressedForMaintenance,
       switchingMatrixModuleFailure,
       lanConnectionPolarityReversed,
       autonomousPMReportMessageInhibited,
       ioSlotToXCONCommunicationFailure,
       stsPathTraceIdentifierMismatch,
       nePowerFailureAtConnectorA,
       nePowerFailureAtConnectorB,
       freeMemoryOnCardVeryLow,
       freeMemoryOnCardNearZero,
       exerciseRequestOnRing,
       exerciseRequestOnSpan,
       squelchingPath,
       extraTrafficPreempted,
       farEndLockoutOfWorkingRing,
       farEndLockoutOfWorkingSpan,
       farEndLockoutOfProtectionRing,
       farEndLockoutOfProtectionAllSpans,
       farEndWorkingFacilityForcedToSwitchToProtectionRing,
       farEndWorkingFacilityForcedToSwitchToProtectionSpan,
       farEndManualSwitchOfWorkingFacilityToProtectionRing,
       farEndManualSwitchOfWorkingFacilityToProtectionSpan,
       farEndExercisingRing,
       farEndExercisingSpan,
       farEndBERThresholdPassedForSignalFailureRing,
       farEndBERThresholdPassedForSignalFailureSpan,
       farEndBERThresholdPassedForSignalDegradeRing,
       farEndBERThresholdPassedForSignalDegradeSpan,
       apsChannelFarEndProtectionLineSignalDegrade,
       ringSwitchIsActiveOnTheEastSide,
       ringSwitchIsActiveOnTheWestSide,
       spanSwitchIsActiveOnTheEastSide,
       spanSwitchIsActiveOnTheWestSide,
       uniDirectionalFullPassThroughIsActive,
       biDirectionalFullPassThroughIsActive,
       kBytesPassThroughIsActive,
       ringIsSegmented,
       ringTopologyIsUnderConstruction,
       lockoutOfProtectionAllSpans,
       farEndOfFiberIsProvisionedWithDifferentRingID,
       bothEndsOfFiberProvisionedAsEastOrBothAsWest,
       autonomousMessagesInhibited,
       trafficStormOnLANLANTemporarilyDisabled,
       reptdbchgMessagesInhibited,
       securityUserIDHasExpired,
       partialFanFailure,
       forcedSwitchRequestOnRing,
       forcedSwitchRequestOnSpan,
       lockoutSwitchRequestOnRing,
       lockoutSwitchRequestOnSpan,
       manualSwitchRequestOnRing,
       manualSwitchRequestOnSpan,
       communicationFailurePeerToPeerSlotControlBusA,
       communicationFailurePeerToPeerSlotControlBusB,
       controllerAToShelfSlotCommunicationFailure,
       controllerBToShelfSlotCommunicationFailure,
       interconnectionEquipmentFailureWorkingPayloadBus,
       interconnectionEquipmentFailureProtectPayloadBus,
       inhibitSwitchToProtectRequestOnEquipment,
       inhibitSwitchToWorkingRequestOnEquipment,

       exercisingRingSuccessfully,
       exercisingSpanSuccessfully,
       spanIsInWaitToRestoreState,
       exerciseRequestOnRingFailed,
       exerciseRequestOnSpanFailed,
       farEndLockoutOfProtectionSpan,

       manufacturingDataMemoryEEPROMFailure,
       replaceableEquipmentOrUnitIsMissing,
       softwareDownloadFailed,
       extraTrafficPCADropped,

       etherTxOversubscribed,
       etherRxOverSubscribed,
       etherTxExcessFlowCtrl,
       etherRxExcessFlowCtrl,
       transportLayerFailure,
       etherTxUnderrun,
       synchronizationReferenceFrequencyOutOfBounds,
       ntpOrSntpHostFailure,
       peerCardNotResponding,
       alarmsAndEventsSuppressedForThisObject,
       ds3FrameFormatMismatch,

       timSectionTraceIdentifierMismatchFailure,
       aisMultiplexSectionAlarmIndicationSignal,
       rfiMultiplexSectionRemoteFailureOrAlarmIndication,
       timHighOrderTraceIdentifierMismatchFailure,
       aisAdministrationUnitAlarmIndicationSignal,
       lopAdministrationUnitLossOfPointer,
       slmfUnequippedHighOrderPathUnequipped,
       slmfPLMHighOrderPathLabelMismatch,
       rfiHighOrderRemoteFailureOrAlarmIndication,
       lopTributaryUnitLossOfPointer,
       aisTributaryUnitAlarmIndicationSignal,
       slmfUnequippedLowOrderPathUnequipped,
       slmfPLMLowOrderPathLabelMismatch,
       timLowOrderTraceIdentifierMismatchFailure,
       rfiLowOrderRemoteFailureOrAlarmIndication,
       g811PrimaryReferenceClockTraceable,
       g812TransitNodeClockTraceable,
       g812LocalNodeClockTraceable,
       g813SynchronousEquipmentTimingSourceTraceable,
       e1LoopbackDueToFEACCommand,
       e1LoopbackCommandSentToFarEnd,
       e3LoopbackDueToFEACCommand,
       farEndMultipleE1LOSDetectedOnE3,
       farEndE1EqptFailNonServiceAffecting,
       farEndE1EqptFailServiceAffecting,
       farEndSingleE1LOS,
       farEndE3EqptFailServiceAffecting,
       e3LoopbackCommandSentToFarEnd,
       farEndE3EqptFailNonServiceAffecting,
       lowVoltBatteryA,
       highVoltBatteryA,
       lowVoltBatteryB,
       highVoltBatteryB,
       msspRingOutOfSync,
       msspMultiNodeTableUpdateCompleted,
       automaticSNCPSwitchCausedByAIS,
       automaticSNCPSwitchCausedByLOP,
       automaticSNCPSwitchCausedByUNEQ,
       automaticSNCPSwitchCausedByPDI,
       automaticSNCPSwitchCausedBySFBER,
       automaticSNCPSwitchCausedBySDBER,
       stmConcatenationError,
       e3IdleCondition,
       channelMSSPInconsistentAPSCode,
       channelMSSPImproperAPSCodeAPS,
       channelMSSPNodeIdMismatchAPS,
       channelMSSPDefaultKAPS,
       channelMSSPConnectionLossAPS,
       minimumClockTraceableSDH,
       lineIsInWaitToRestoreStateSDH,
       berThresholdExceededForSignalDegradeHighOrder,
       berThresholdExceededForSignalFailureHighOrder,
       berThresholdExceededForSignalDegradeLowOrder,
       berThresholdExceededForSignalFailureLowOrder,
       failureToSwitchToProtectionHighOrderPath,
       failureToSwitchToProtectionLowOrderPath,
       a8b10bOutOfSync,
       odukPMAlarmIndicationSignal,
       otukAlarmIndicationSignal,
       otukSMBackwardDefectIndication,
       fecUncorrectedWord,
       gccTerminationFailure,
       otukIncomingAlignmentError,
       odukLockedDefectPM,
       lossOfMultiFrame,
       odukOpenConnectionIndication,
       payloadTypeIdentifierMismatch,
       odukTrailTraceIdentifierMismatch,
       otukTrailTraceIdentifierMismatch,
       equipmentHighLaserBias,
       equipmentHighLaserTemp,
       equipmentHighLaserPeltier,
       equipmentHighRxPower,
       equipmentHighTxPower,
       equipmentHighTransceiverVoltage,
       equipmentLowLaserBias,
       equipmentLowLaserTemp,
       equipmentLowLaserPeltier,
       equipmentLowRxPower,
       equipmentLowTxPower,
       equipmentLowTransceiverVoltage,
       equipmentRxLocked,
       equipmentSquelched,
       equipmentTxLocked,
       otukSignalFailure,
       odukSignalFailure,
       otukSignalDegrade,
       odukSignalDegrade,
       pluggablePortMissing,
       pluggablePortRateMismatch,
       pluggablePortSecurityCodeMismatch,
       tciNotSelected,
       tci1ClockFailure,
       odukPMBackwardDefectIndication,
       odukTCM1BackwardDefectIndication,
       odukTCM2BackwardDefectIndication,
       equipmentHighRxTemperature,
       equipmentLowRxTemperature,
       opticalChannelDeactivationFailure,
       opticalNetworkTypeMismatch,
       networkTopologyIncomplete,
       lossOfChannel,
       fecMismatch,
       timSectionMonitorTraceIdentifierMismatchFailure,
       automaticLaserShutdown,
       tci2ClockFailure,
       equipmentWavelengthMismatch,
       dspCommunicationFailure,
       dspFailure,
       laserApproachingEndOfLife,
       crossconnectLoopback,
       adminLogoutOfUser,
       userLockedOut,
       adminLockoutOfUser,
       adminLockoutClear,
       invalidLoginUsername,
       securityInvalidLoginPassword,
       securityInvalidLoginLockedOut,
       securityInvalidLoginAlreadyLoggedOn,
       loginOfUser,
       automaticLogoutOfIdleUser,
       logoutOfUser,
       firewallHasBeenDisabled,
       connectionEquipmentMismatch,
       disableInactiveUser,
       disableInactiveClear,
       batteryFailure,
       extremeHighVolt,
       extremeLowVolt,
       highVolt,
       lowVolt,
       suspendUser,
       suspendUserClear,
       lineDccTerminationFailure,
       multiplexSectionDccTerminationFailure,
       gigaBitEthernetOutOfSync,
       sequenceMismatch,
       lossOfAlignment,
       outOfUseByAdministrativeCommand,
       outOfUseTransportFailure,
       vcatGroupDown,
       vcatGroupDegraded,
       vcatGroupIncomplete,
       alarmIndicationSignalInTX,
       remoteAlarmIndicationInTX,
       kByteAPSChannelFailure,
       apsInvalidMode,
       ipAddressAlreadyInUseWithinTheSameDccArea,
       nodeNameInUseWithinTheSameDccArea,
       rearPanelEthernetLinkRemoved,
       manualSwitchToProtectResultedInNoTrafficSwitch,
       manualSwitchBackToWorkingResultedInNoTrafficSwitch,
       forcedSwitchToProtectResultedInNoTrafficSwitch,
       forcedSwitchBackToWorkingResultedInNoTrafficSwitch,
       duplicateSerialNumberDetectedOnAPluggableEntity,
       lossOfSignalForOpticalChannel,
       encapsulationMismatchPath,
       encapsulationMismatchVT,
       encapsulationMismatchHighOrderPath,
       encapsulationMismatchLowOrderPath,
       improperMatrixEquipmentInserted,
       eqptProblemOnCarrierOrPIM,
       eqptProblemOnPIMOrPPM,
       portFAIL,
       unreachablePortTargetPower,
       portAddPowerDegradeLow,
       portAddPowerDegradeHigh,
       portAddPowerFailLow,
       portAddPowerFailHigh,
       gfpUserPayloadMismatch,
       gfpFibreChannelDistanceExtensionMismatch,
       gfpFibreChannelDistanceExtensionBufferStarvation,
       gfpFibreChannelDistanceExtensionCreditStarvation,
       gfpClientSignalFailDetected,
       gfpLossOfFrameDelineation,
       gfpExtensionHeaderMismatch,
       lcasVcgMemberTxSideInAddState,
       lcasVcgMemberTxSideInDnuState,
       lcasControlWordCrcCheckFailure,
       lcasVcgMemberRxSideInFailState,
       signalLossOnDataInterface,
       synchronizationLossOnDataInterface,
       automaticWdmAnsFinished,
       incomingOverheadSignalAbsent,
       opticalSafetyRemoteInterlockOn,
       automaticPowerControlCorrectionSkipped,
       apcCannotSetValueDueToRangeLimits,
       farEndManualSwitchBackToWorkingSpan,
       pluginModuleRangeSettingsMismatch,
       automaticPowerControlTerminatedOnManualRequest,
       oduk1AlarmIndicationSignal,
       oduk2AlarmIndicationSignal,
       oduk3AlarmIndicationSignal,
       oduk4AlarmIndicationSignal,
       temperatureReadingMismatchBetweenSCCards,
       voltageReadingMismatchBetweenSCCards,
       alarmsSuppressedonOutOfGroupVcatMember,
       blsrSoftwareVersionMismatch,
       optimized1Plus1ApsPrimaryFacility,
       optimized1Plus1ApsPrimarySectionMismatch,
       optimized1Plus1ApsInvalidPrimarySection,
       compositeClockHighLineVoltage,
       berThresholdExceededForSignalDegradeVt,
       berThresholdExceededForSignalFailureVt,
       spanLengthOutOfRange,
       idleSignalCondition,
       idleSignalConditionInTx,
       vtPathTraceIdentifierMismatch,
       lossOfFrameInTX,
       provisioningMismatch,
       sectionTraceIdentifierMismatch,
       regeneratorSectionTraceIdentifierMismatch,
       switchingMatrixModuleFailureWorking,
       switchingMatrixModuleFailureProtect,
       slotCommunicationDisabled,
       sessionTimeLimitExpired,
       userPasswordChangeRequired,
       isisAdjacencyFailure,
       msspSoftwareVersionMismatch,
       remoteAuthenticationFailSeeAuditLog,
       illegalRouteAdditionToNetwork,
       ringIsSquelchingStsTraffic,
       ringIsSquelchingVtTraffic,
       archiveOfAuditLogFailed,
       rprWrapped,
       shelfCommunicationFailure,
       duplicatedShelfIdentifier,
       softwareMismatch,
       lmpFailure,
       opticalTerminationIncomplete,
       forwardDefectIndication,
       payloadMissingIndication,
       spanMeasurementCannotBePerformed,
       ringIsSquelchingHighOrderTraffic,
       ringIsSquelchingLowOrderTraffic,
       badPacketCountExceedsThreshold,
       linkLayerKeepAliveFailure,
       autonegotiationRemoteFailureIndication,
       trailSignalFail,
       ds1LoopbackCommandSentToFarEnd,
       multiplexSectionSignalDegraded,
       multiplexSectionExcessiveErrors,
       highOrderPathSignalDegraded,
       highOrderPathExcessiveErrors,
       lowOrderPathSignalDegraded,
       lowOrderPathExcessiveErrors,
       regeneratorSectionDccTerminationFailure,
       networkMemoryPoolLow,
       ospfRoutingTableOverflow,
       autoLaserShutdownDisabled,
       wavelengthOutOfLock,
       rprProtectionIsActive,
       maxRPRStationNumberExceeded,
       rprProtectionConfigurationMismatched,
       reservedBandwidthLinkRateExceededOnRinglet0,
       reservedBandwidthLinkRateExceededOnRinglet1,
       rprInterfaceInPassThroughMode,
       rprPeerNodeIsMissing,
       rprRiFailure,
       rprSignalFailure,
       rprSignalDegrade,
       interlinkFailure,
       apcWrongGain,
       rprSpanMismatch,
       fastAutomaticProtectionSwitching,
       fastAutomaticProtectionSwitchingConfigMismatch,
       lcasSinkGroupError,
       lcasVCGMemberRxSideInDNUState,
       fcDistanceExtFuncNotEstablished,
       nonCiscoPPMInserted,
       unqualifiedPPMInserted,
       ftaMismatch,
       cardPortsUnableToProvideProtection,
       lmpSignalDegrade,
       lmpSignalFailure,
       lmpUnallocatedDataLink,
       frontPortLinkLoss,
       bertEnabled,
       bertSynchronizationStatusFailed,
       workQueueFull,
       enhancedRemoteFailureIndicationPathServer,
       enhancedRemoteFailureIndicationPathConnectivity,
       enhancedRemoteFailureIndicationPathPayload,
       securityIntrusionDetPwd,
       securityIntrusionDetUser,
       forcedSwitchToPrimaryReference,
       forcedSwitchToSecondReference,
       forcedSwitchToThirdReference,
       forcedSwitchToInternalClock,
       industrialHighTemperature,
       opticalPowerDegradeLow,
       automaticPowerControlFailure,
       opticalPowerDegradeHigh,
       automaticPowerControlDisabled,
       opticalPowerFailureLow,
       ringIdMismatch,
       opticalPowerFailureHigh,
       lossOfContinuity,
       variableOpticalAttenuatorDegradeLow,
       variableOpticalAttenuatorDegradeHigh,
       variableOpticalAttenuatorFailureLow,
       variableOpticalAttenuatorFailureHigh,
       laserBiasDegrade,
       laserBiasFailure,
       laserTemperatureDegrade,
       opticalAmplifierGainDegradeLow,
       opticalAmplifierGainDegradeHigh,
       opticalAmplifierGainFailureLow,
       opticalAmplifierGainFailureHigh,
       opticalChannelConnectionFailure,
       opticalChannelActivationFailure,
       laserAutoPowerReduction,
       caseTemperatureDegrade,
       fiberTemperatureDegrade,
       shutterOpen,
       awgTemperatureDegrade,
       awgTemperatureFailure,
       awgOverTemperature,
       opticalAmplifierInitialization,
       awgWarmUp,
       incSigloss,
       incSyncloss,
       incGfpOutOfFrame,
       incGfpSigLoss,
       incGfpSyncLoss,
       waitToRestore,
       extremeHighVoltBatteryA,
       extremeLowVoltBatteryA,
       extremeHighVoltBatteryB,
       extremeLowVoltBatteryB,
       iosConfigCopyFailed,
       iosConfigCopyInProgress,
       signalingUnableToSetupCircuit,
       errorInStartupConfig,
       noStartupConfig,
       needToSaveRunningConfig,
       invalidAlarm,
       rsvpHelloFSMToNeighborDown,
       securityInvalidLoginUsername,
       databaseBackupFailed,
       databaseRestoreFailed,
       lmpHelloFSMToControlChannelDown,
       lmpNeighborDiscoveryHasFailed,
       unauthorizedIncomingSignalingRequest,
       auditLog80PercentFull,
       moduleCommunicationFailure,
       auditLog100PercentFullOldestRecordsWillBeLost,
       standbyDatabaseOutOfSync,
       redundantPowerCapabilityLost,
       lofAdministrationUnitLossOfMultiFrame,
       sdhSpanIsInWaitToRestoreState,
       equipmentPowerFailureAtConnectorA,
       equipmentPowerFailureAtConnectorB,
       equipmentPowerFailureAtReturnConnectorA,
       equipmentPowerFailureAtReturnConnectorB,
       loginFailThresholdExceeded,
       connectionIdMismatchOnMatrixA,
       connectionIdMismatchOnMatrixB,
       equipmentFailureHighTemperature,
       laserBiasCurrentHigh,
       highLaserTemperature,
       bridgeAndRollHasOccurred,
       bridgeAndRollIsPendingAValidSignal,
       farEndForcedSwitchBackToWorkingSpan,
       partialFanFailurePartsFailure,
       unprotectedSyncronizationEquipment,
       unprotectedMatrixEquipment,
       matrixEquipmentUnavailable,
       controlBusFailureTscA,
       controlBusFailureTscB,
       payloadBusFailureMatrixA,
       payloadBusFailureMatrixB,
       matrixOperationSuspended,
       clockFailureTsc,
       payloadLoopback,
       dccChannelLoss,
       reptPmMsgInhibited,
       loopbackCrs,
       syncRefFreqOutOfBound,
       systemUpgradeInProgress,
       eqptFailToBoot,
       eqptPowerFailure,
       clockBusFailureTscA,
       clockBusFailureTscB,
       powerFuseFailure,
       controlCommunicationsEquipmentFailure,
       differentSoftwareVersion,
       ospfHelloFail,
       clockModuleFrequencyMismatch,
       etherPortSwitch,
       openIOSlots,
       odukTCM1AlarmIndicationSignal,
       odukTCM2AlarmIndicationSignal,
       odukLockedDefectTCM1,
       odukLockedDefectTCM2,
       otukLossOfFrame,
       odukOpenConnectionIndicationTCM1,
       odukOpenConnectionIndicationTCM2,
       odukTrailTraceIdentifierMismatchTCM1,
       odukTrailTraceIdentifierMismatchTCM2,
       odukSignalFailureTCM1,
       odukSignalFailureTCM2,
       odukSignalDegradeTCM1,
       odukSignalDegradeTCM2,
       equipmentBootInProgress,
       lossOfClockFromMateShelfController,
       dcuLossFailure,
       ochncMaintenance,
	   alarmIndicationSignalInTXCustomerInstallation,
	   remoteAlarmIndicationInTXCustomerInstallation,
       shutterInsertionLossVariationDegradeLow,
       shutterInsertionLossVariationDegradeHigh,
       pluginModuleCommunicationFailure,
       universalTransponderModuleHardwareFailure,
       universalTransponderModuleCommunicationFailure,
       berThresholdExceededForSignalDegradeLine,
       berThresholdExceededForSignalDegradePath,
       berThresholdExceededForSignalFailureLine,
       berThresholdExceededForSignalFailurePath,
       opticalChannelIncomplete
     }
        STATUS current
        DESCRIPTION
          "The generic notifications for Cisco ONS 
           network device, ONS 15327, 15310"
        ::= { cerentGenericGroups 30 }

-- This definition of group will move to a cerentCommon modules
-- eventually. 
        
cerentGenericCommonGroup OBJECT-GROUP
        OBJECTS {
          cerentGenericEnableNotification,
          cerentGenericNodeTime,
          cerentGenericSentNotifications,
          cerentGenericLastChangeTime,  
          cerentGenericMultishelfEnabled
          }
        STATUS current
        DESCRIPTION
          "The objects related to traps dispatch"
        ::= { cerentGenericGroups 40 }

-- This group covers for threshold display and TCA trap

cerentThresholdGroup OBJECT-GROUP
        OBJECTS {
          cerentGenericThresholdMonitorType,
          cerentGenericThresholdLocation,
          cerentGenericThresholdPeriod,
          cerentGenericThresholdSetValue,
          cerentGenericThresholdCurrentValue,
          cerentGenericThresholdDetectType
        }
        STATUS current
        DESCRIPTION
          "The objects for storing all the current alarms"
        ::= { cerentGenericGroups 50 }

eventGenericDeprecatedGroup NOTIFICATION-GROUP
     NOTIFICATIONS {
       controlEquipmentControlCommunicationsEquipmentFailure,
       securityInvalidLoginUsernameSeeAuditTrail,
       manufacturingEepromFailure,
       airFlow
     }
        STATUS deprecated
        DESCRIPTION
          "The deprecated notifications for Cisco ONS 
           network devices"
        ::= { cerentGenericGroups 60 }

reportedAlarmGenericGroup OBJECT-GROUP
        OBJECTS {
          cerentGenericReportedAlarmCount,
          cerentGenericReportedAlarmObjectType,
          cerentGenericReportedAlarmSlotNumber,
          cerentGenericReportedAlarmPortNumber,
          cerentGenericReportedAlarmObjectIndex,
          cerentGenericReportedAlarmType,
          cerentGenericReportedAlarmTimeStamp,
          cerentGenericReportedAlarmObjectName,
          cerentGenericReportedAlarmAdditionalInfo,
          cerentGenericReportedAlarmSeverity,
          cerentGenericReportedAlarmStatus,
          cerentGenericReportedAlarmServiceAffecting
        }
        STATUS current
        DESCRIPTION
          "The group for reported alarm objects"
        ::= { cerentGenericGroups 70 }
        

-- the compliance specification for agent developers

cerentGenericBasicCompliance MODULE-COMPLIANCE
       STATUS current
       DESCRIPTION
         "The basic implementation requirements 
          for Cisco ONS network device, ONS 15327, 15310 "
       MODULE
         MANDATORY-GROUPS {
           nodeGenericGroup,
           eventGenericGroup
        }
       ::= { cerentCompliance 10 }
          
END
